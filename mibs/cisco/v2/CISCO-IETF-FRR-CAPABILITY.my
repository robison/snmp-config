-- *****************************************************************
-- CISCO-IETF-FRR-CAPABILITY.my:  Capability statement for Cisco's
-- 	implementation of the IETF's MPLS Traffic Engineering Fast
-- 	Reroute MIB (CISCO-IETF-FRR-MIB.my)
--
-- April 25, 2003 - Adrien Grise
--
-- Copyright (c) 2003 by cisco Systems, Inc.
-- All rights reserved.
-- 
-- *****************************************************************

CISCO-IETF-FRR-CAPABILITY DEFINITIONS ::= BEGIN

IMPORTS
   MODULE-IDENTITY
      FROM SNMPv2-SMI

   AGENT-CAPABILITIES 
      FROM SNMPv2-CONF
   
   ciscoAgentCapability
      FROM CISCO-SMI;


ciscoIetfFrrCapability MODULE-IDENTITY
   LAST-UPDATED
      "200305231200Z" -- 23 May 2003 12:00:00
   ORGANIZATION
      "Cisco Systems, Inc."
   CONTACT-INFO
          "             Cisco Systems
                        Customer Service

                Postal: 170 W. Tasman Drive
                        San Jose, CA  95134
                        USA

                Tel: +1 800 553-NETS

                E-mail: mpls-mib@cisco.com"
   DESCRIPTION
          "Agent capabilities for CISCO-IETF-FRR-MIB"

   -- Revision history.

   REVISION
          "200305231200Z" -- 23 May 2003 12:00:00
   DESCRIPTION
          "Initial version."

   ::= { ciscoAgentCapability 310 }

ciscoIetfFrrCapabilityV12R0026S AGENT-CAPABILITIES

PRODUCT-RELEASE "Cisco IOS 12.0(26)S"
STATUS      current
DESCRIPTION "MPLS Traffic Engineering Fast Reroute MIB capabilities"

SUPPORTS    CISCO-IETF-FRR-MIB
INCLUDES    { cmplsFrrNotif,
              cmplsFrrScalars,
              cmplsFrrObjects,
              cmplsFrrScalarGroup,
              cmplsFrrConstGroup,
              cmplsFrrLogGroup,
              cmplsFrrFacRouteDBGroup,
              cmplsFrrNotifGroup
            }

    ::= { ciscoIetfFrrCapability 1 }

END
