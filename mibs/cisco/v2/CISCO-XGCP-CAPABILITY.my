-- *****************************************************************
-- CISCO-XGCP-CAPABILITY
--
-- AGENT-CAPABILITIES mib for CISCO-XGCP-MIB
-- 
-- October 2002, Feng Luo 
--
-- Copyright (c) 2002, 2004, 2005, 2006 by Cisco Systems, Inc.
--
-- *****************************************************************

CISCO-XGCP-CAPABILITY DEFINITIONS ::= BEGIN
IMPORTS
        MODULE-IDENTITY,
        Integer32
                FROM SNMPv2-SMI
        AGENT-CAPABILITIES
                FROM SNMPv2-CONF
        ciscoAgentCapability
                FROM CISCO-SMI
        InetAddressType
                FROM INET-ADDRESS-MIB
        CiscoPort
                FROM CISCO-TC
        CMgcGroupIndexOrZero
                FROM CISCO-MGC-MIB
        CCallControlProfileIndexOrZero
                FROM CISCO-MEDIA-GATEWAY-MIB
        CXgcpRetryMethod 
                FROM CISCO-XGCP-MIB;


ciscoXgcpCapability MODULE-IDENTITY
    LAST-UPDATED "200603010000Z"
    ORGANIZATION "Cisco Systems, Inc."
    CONTACT-INFO
        "        Cisco Systems
                 Customer Service
        Postal: 170 W Tasman Drive
                San Jose, CA 95134
                USA
           Tel: +1 800 553-NETS
        E-mail: cs-voice-gateway@cisco.com"
    DESCRIPTION "The agent capabilities for CISCO-XGCP-MIB." 

        REVISION "200603010000Z"
        DESCRIPTION
            "Deprecated ciscoXgcpCapabilityV12R03AS5000 and added
             ciscoXgcpCapabilityV12R04AS5000."

        REVISION "200602140000Z"
        DESCRIPTION
            "Added ciscoXgcpCapabilityV5R300 for 
             MGX8880 release 5.3.00.
             Deprecated ciscoXgcpCapabilityV12R03 and added
             ciscoXgcpCapabilityV12R03AS5000."

        REVISION "200506240000Z"
        DESCRIPTION
            "Added ciscoXgcpCapabilityV5R100 for 
             MGX8850 release 5.1.00"
            
        REVISION "200501060000Z"
        DESCRIPTION
            "Fixed syntax error in cXgcpMediaGwSupportedPackages
             of ciscoXgcpCapabilityV12R03." 

        REVISION "200410040000Z"
        DESCRIPTION
            "Added ciscoXgcpCapabilityV5R015 for 
             MGX8850 release 5.0.15"
            
        REVISION "200406160000Z"
        DESCRIPTION
            "Added ciscoXgcpCapabilityV12R03 for Cisco IOS 12.3."
            
        REVISION "200212310000Z"
        DESCRIPTION
            "Initial version of this MIB module."
        ::= { ciscoAgentCapability 408 }


ciscoXgcpCapabilityV4R010 AGENT-CAPABILITIES

PRODUCT-RELEASE "MGX8850 Release 4.0"
STATUS          current
DESCRIPTION     "XGCP MIB capabilities for VXSM in Release 4.0.10." 

SUPPORTS CISCO-XGCP-MIB
INCLUDES { 
           cXgcpMgcConfigGroup, 
           cXgcpMediaGwGroup, 
           cXgcpMsgStatsGroup 
         }

    VARIATION       cXgcpMgcConfigAddrType
    SYNTAX          INTEGER { ipv4(1) }
    ACCESS          read-only
    DESCRIPTION     "VXSM only supports 'ipv4' type."

    VARIATION       cXgcpMgcConfigAddress
    SYNTAX          OCTET STRING (SIZE(4))
    DESCRIPTION     "VXSM only supports 'InetAddressIPv4' format."

    VARIATION       cXgcpMgcConfigProtocolIndex
    SYNTAX          Integer32 (1..1)
    DESCRIPTION     "There are only 1 protocol supported in the 
                     this release."

    VARIATION       cXgcpMediaGwDefaultPackage
    DEFVAL          { packageT } 
    DESCRIPTION     "The default package in VXSM is packageT."

    VARIATION       cXgcpMediaGwQuarantineLoop
    DEFVAL          { false } 
    DESCRIPTION     "The default value in VXSM is false."

    VARIATION       cXgcpMediaGwMaxMsgSize
    SYNTAX          Integer32 (512..60000)
    DEFVAL          { 60000 }
    DESCRIPTION     "The valid range is 512 to 60000.
                     The initial value is 60000."

    VARIATION       cXgcpMsgStatsMgcIPAddressType
    SYNTAX          INTEGER { ipv4(1) }
    DESCRIPTION     "VXSM only supports 'ipv4' type."

    VARIATION       cXgcpMsgStatsMgcIPAddress
    SYNTAX          OCTET STRING (SIZE(4))
    DESCRIPTION     "VXSM only supports 'InetAddressIPv4' format."

    VARIATION       cXgcpMediaGwRequestRetryMethod
    ACCESS          not-implemented
    DESCRIPTION     "not supported in VXSM."

    ::= { ciscoXgcpCapability 1 }

ciscoXgcpCapabilityV12R03 AGENT-CAPABILITIES

PRODUCT-RELEASE "Cisco IOS 12.3"
STATUS          obsolete -- superceded by ciscoXgcpCapabilityV12R03AS5000
DESCRIPTION     "Cisco XGCP MIB capabilities"

    SUPPORTS        CISCO-XGCP-MIB
    INCLUDES        { 
                      cXgcpMgcConfigGroup, 
                      cXgcpMediaGwGroup, 
                      cXgcpMsgStatsGroup
                    }
     
    VARIATION       cXgcpMgcConfigMgcGrpNum 
    SYNTAX          CMgcGroupIndexOrZero (0)
    ACCESS          read-only 
    DESCRIPTION     "IOS does not allow to associate any MGC group."

    VARIATION       cXgcpMgcConfigAddrType
    SYNTAX          InetAddressType { unknown(0), ipv4(1), dns(16) }
    ACCESS          read-only
    DESCRIPTION     "IOS supports only IPV4 addresses and DNS names as
                     Media Gateway Controller address."

    VARIATION       cXgcpMgcConfigAddress
    ACCESS          read-only
    DESCRIPTION     "Write not implemented."

    VARIATION       cXgcpMgcConfigProtocolIndex
    ACCESS          not-implemented 
    DESCRIPTION    "This object is currently not implemented."

    VARIATION       cXgcpMgcConfigGatewayUdpPort
    SYNTAX          CiscoPort (1025..65535)
    ACCESS          read-only
    DESCRIPTION     "IOS does not allow to set the MGCP port to
                     well-known ports, 0 to 1024."

    VARIATION       cXgcpMediaGwRequestTimeOut
    ACCESS          read-only
    DESCRIPTION     "Write not implemented."

    VARIATION       cXgcpMediaGwRequestRetries
    ACCESS          not-implemented 
    DESCRIPTION     "This object is currently not implemented."

    VARIATION       cXgcpMediaGwRequestRetryMethod
    SYNTAX          CXgcpRetryMethod { resetTimerForEndpoint (4) }
    ACCESS          read-only
    DESCRIPTION     "IOS supports only resetTimerForEndpoint method."
                     
    VARIATION       cXgcpMediaGwMaxExpTimeout
    ACCESS          read-only
    DESCRIPTION     "Write not implemented."
 
    VARIATION       cXgcpMediaGwRestartMwd
    ACCESS          read-only
    DESCRIPTION     "Write not implemented."

    VARIATION       cXgcpMediaGwRestartDelay
    ACCESS          read-only
    DESCRIPTION     "Write not implemented."

    VARIATION       cXgcpMediaGwDefaultPackage
    SYNTAX          INTEGER 
                    { 
                       packageG(2), packageD(3), packageM(4), 
                       packageT(5), packageL(6), packageR(8), 
                       packageN(9), packageA(10),packageS(11), 
                       packageMS(13), packageDT(14), packageMO(15), 
                       packageRES(16),  packageIT(18), packageMT(19), 
                       packageFXR(23)
                    }
    ACCESS          read-only
    DEFVAL          { packageT }
    DESCRIPTION     "Write not implemented. All packages not supported.
                     Default value is Trunk Package."

    VARIATION       cXgcpMediaGwSupportedPackages
    SYNTAX          BITS
                    { 
                      packageG(2), packageD(3), packageM(4), 
                      packageT(5), packageL(6), packageR(8), 
                      packageN(9), packageA(10), packageS(11), 
                      packageMS(13),  packageDT(14), packageMO(15), 
                      packageRES(16), packageIT(18), packageMT(19), 
                      packageFXR(23) 
                    }
    DESCRIPTION     "IOS supports only Dont care, Generic, DTMF, Trunk
                     Line, RTP, NAS, Announcement Server, Script, 
                     MF CAS, DTMF CAS, MO, RES, IT, MT and FAX 
                     packages"

    VARIATION       cXgcpMediaGwSimpleSdpEnabled
    ACCESS          read-only
    DESCRIPTION     "Write not implemented."

    VARIATION       cXgcpMediaGwAckSdpEnabled
    ACCESS          read-only
    DESCRIPTION     "Write not implemented."

    VARIATION       cXgcpMediaGwUndottedNotation
    ACCESS          read-only
    DESCRIPTION     "Write not implemented."

    VARIATION       cXgcpMediaGwQuarantineProcess
    ACCESS          read-only
    DESCRIPTION     "Write not implemented."

    VARIATION       cXgcpMediaGwQuarantineLoop
    ACCESS          read-only
    DESCRIPTION     "Write not implemented."

    VARIATION       cXgcpMediaGwQuarantinePersist
    ACCESS          read-only
    DESCRIPTION     "Write not implemented."

    VARIATION       cXgcpMediaGwPiggybackMsg
    ACCESS          read-only
    DESCRIPTION     "Write not implemented."

    VARIATION       cXgcpMediaGwMaxMsgSize
    SYNTAX          Integer32 (0)
    ACCESS          read-only 
    DESCRIPTION     "IOS does not impose any limit on the maximum size
                     of the message."

    VARIATION       cXgcpMediaGwLastFailMgcAddrType
    ACCESS          not-implemented 
    DESCRIPTION     "This object is currently not implemented."

    VARIATION       cXgcpMediaGwLastFailMgcAddr
    ACCESS          not-implemented 
    DESCRIPTION     "This object is currently not implemented."

    VARIATION       cXgcpMediaGwDtmfRelay
    ACCESS          not-implemented 
    DESCRIPTION     "This object is currently not implemented."

    VARIATION       cXgcpMsgStatsMgcIPAddressType
    SYNTAX          InetAddressType { unknown(0), ipv4(1), dns(16) }
    DESCRIPTION     "IOS supports only IPV4 addresses and DNS names as
                     Media Gateway Controller address."

    VARIATION       cXgcpMsgStatsIncompleteMessages
    ACCESS          not-implemented
    DESCRIPTION     "This object is currently not implemented."

    ::= { ciscoXgcpCapability 2 }

ciscoXgcpCapabilityV5R015 AGENT-CAPABILITIES

PRODUCT-RELEASE "MGX8850 release 5.0.15"
STATUS          current
DESCRIPTION     "XGCP MIB capabilities for VXSM in 
                 MGX8850 release 5.0.15." 

    SUPPORTS        CISCO-XGCP-MIB
        INCLUDES    { 
                      cXgcpMgcConfigGroup,
                      cXgcpMediaGwGroup, 
                      cXgcpMsgStatsGroup 
                    }

        VARIATION       cXgcpMgcConfigAddrType
            SYNTAX      INTEGER { ipv4(1) }
            ACCESS      read-only
            DESCRIPTION "VXSM only supports 'ipv4' type and read-only."

        VARIATION       cXgcpMgcConfigAddress
            SYNTAX      OCTET STRING (SIZE(4))
            DESCRIPTION "VXSM only supports 'InetAddressIPv4' format."

        VARIATION       cXgcpMgcConfigProtocolIndex
            SYNTAX      Integer32 (1..1)
            DESCRIPTION "There are only 1 protocol supported in the 
                         this release."

        VARIATION       cXgcpMediaGwDefaultPackage
            DEFVAL      { packageIT } 
            DESCRIPTION "The default package in VXSM is packageT."

        VARIATION       cXgcpMediaGwQuarantineLoop
            DEFVAL      { false } 
            DESCRIPTION "The default value in VXSM is false."

        VARIATION       cXgcpMsgStatsMgcIPAddressType
            SYNTAX      INTEGER { ipv4(1) }
            DESCRIPTION "VXSM only supports 'ipv4' type."

        VARIATION       cXgcpMsgStatsMgcIPAddress
            SYNTAX      OCTET STRING (SIZE(4))
            DESCRIPTION "VXSM only supports 'InetAddressIPv4' format."

        VARIATION       cXgcpMediaGwMaxExpTimeout
            SYNTAX      Integer32 (1..10000)
            DEFVAL      { 4000 }
            DESCRIPTION "The supported range is 1 to 10000."

        VARIATION       cXgcpMediaGwMaxMsgSize
            SYNTAX      Integer32 (512..60000)
            DEFVAL      { 60000 }
            DESCRIPTION "The valid range is 512 to 60000.
                         The initial value is 60000."

        VARIATION       cXgcpMediaGwRequestRetries
            ACCESS      not-implemented
            DESCRIPTION "not supported in VXSM."

        VARIATION       cXgcpMediaGwRequestRetryMethod
            ACCESS      not-implemented
            DESCRIPTION "not supported in VXSM."

        VARIATION       cXgcpMediaGwRestartMwd
            ACCESS      read-only
            DESCRIPTION "Cannot be modified."

        VARIATION       cXgcpMediaGwRestartDelay
            ACCESS      read-only
            DESCRIPTION "Cannot be modified."

    ::= { ciscoXgcpCapability 3 }

ciscoXgcpCapabilityV5R100 AGENT-CAPABILITIES

PRODUCT-RELEASE "MGX8880 release 5.1.00"
STATUS          current
DESCRIPTION     "XGCP MIB capabilities for VXSM in 
                 MGX8880 release 5.1.00." 

    SUPPORTS        CISCO-XGCP-MIB
        INCLUDES    { 
                      cXgcpMgcConfigGroup,
                      cXgcpMediaGwGroup, 
                      cXgcpMsgStatsGroup,
                      cXgcpMediaGwGroupSup1 
                    }

        VARIATION       cXgcpMgcConfigAddrType
            SYNTAX      INTEGER { ipv4(1) }
            ACCESS      read-only
            DESCRIPTION "VXSM only supports 'ipv4' type and read-only."

        VARIATION       cXgcpMgcConfigAddress
            SYNTAX      OCTET STRING (SIZE(4))
            DESCRIPTION "VXSM only supports 'InetAddressIPv4' format."

        VARIATION       cXgcpMgcConfigProtocolIndex
            SYNTAX      Integer32 (1..1)
            DESCRIPTION "There are only 1 protocol supported in the 
                         this release."

        VARIATION       cXgcpMediaGwDefaultPackage
            ACCESS          not-implemented 
            DESCRIPTION     "This object is currently not supported."

        VARIATION       cXgcpMediaGwQuarantineLoop
            DEFVAL      { false } 
            DESCRIPTION "The default value in VXSM is false."

        VARIATION       cXgcpMsgStatsMgcIPAddressType
            SYNTAX      INTEGER { ipv4(1) }
            DESCRIPTION "VXSM only supports 'ipv4' type."

        VARIATION       cXgcpMsgStatsMgcIPAddress
            SYNTAX      OCTET STRING (SIZE(4))
            DESCRIPTION "VXSM only supports 'InetAddressIPv4' format."

        VARIATION       cXgcpMediaGwMaxExpTimeout
            SYNTAX      Integer32 (1..10000)
            DEFVAL      { 4000 }
            DESCRIPTION "The supported range is 1 to 10000."

        VARIATION       cXgcpMediaGwMaxMsgSize
            SYNTAX      Integer32 (512..60000)
            DEFVAL      { 60000 }
            DESCRIPTION "The valid range is 512 to 60000.
                         The initial value is 60000."

        VARIATION       cXgcpMediaGwRequestRetries
            ACCESS      not-implemented
            DESCRIPTION "not supported in VXSM."

        VARIATION       cXgcpMediaGwRequestRetryMethod
            ACCESS      not-implemented
            DESCRIPTION "not supported in VXSM."

        VARIATION       cXgcpMediaGwRestartMwd
            ACCESS      not-implemented
            DESCRIPTION "not supported in VXSM."

        VARIATION       cXgcpMediaGwRestartDelay
            ACCESS      not-implemented
            DESCRIPTION "not supported in VXSM."

        VARIATION       cXgcpMediaGwLongDurTimer
            SYNTAX      Integer32 (1..65535)
            DESCRIPTION "The valid range is 1 to 65535."

        VARIATION       cXgcpMediaGwProfile
            SYNTAX      CCallControlProfileIndexOrZero (0..25)
            DESCRIPTION "The valid range is 0 to 25."

        VARIATION       cXgcpMediaGwConfiguredPackages
            SYNTAX      BITS {
                             packageG     (2),
                             packageD     (3),
                             packageM     (4),
                             packageT     (5),
                             packageH     (7),
                             packageR     (8),
                             packageMO    (15),
                             packageIT    (18),
                             packageMT    (19),
                             packageFXR   (23),
                             packageBA    (24)
                        }
            DESCRIPTION "Limited data values are supported."

    ::= { ciscoXgcpCapability 4 }

ciscoXgcpCapabilityV5R300 AGENT-CAPABILITIES

PRODUCT-RELEASE "MGX8880 release 5.3.00"
STATUS          current
DESCRIPTION     "XGCP MIB capabilities for VXSM in 
                 MGX8880 release 5.3.00." 

    SUPPORTS        CISCO-XGCP-MIB
        INCLUDES    { 
                      cXgcpMgcConfigGroup,
                      cXgcpMediaGwGroup, 
                      cXgcpMsgStatsGroup,
                      cXgcpMediaGwGroupSup2 
                    }

        VARIATION       cXgcpMgcConfigAddrType
            SYNTAX      INTEGER { ipv4(1) }
            ACCESS      read-only
            DESCRIPTION "VXSM only supports 'ipv4' type and read-only."

        VARIATION       cXgcpMgcConfigAddress
            SYNTAX      OCTET STRING (SIZE(4))
            DESCRIPTION "VXSM only supports 'InetAddressIPv4' format."

        VARIATION       cXgcpMgcConfigProtocolIndex
            SYNTAX      Integer32 (1..1)
            DESCRIPTION "There are only 1 protocol supported in the 
                         this release."

        VARIATION       cXgcpMediaGwDefaultPackage
            SYNTAX      INTEGER {
                             packageG     (2),
                             packageD     (3),
                             packageT     (5),
                             packageMO    (15),
                             packageIT    (18),
                             packageMT    (19),
                             packageFXR   (23),
                             packageBA    (24)
                        }
            DESCRIPTION "Support subset of xGCP packages."

        VARIATION       cXgcpMediaGwQuarantineLoop
            DEFVAL      { false } 
            DESCRIPTION "The default value in VXSM is false."

        VARIATION       cXgcpMsgStatsMgcIPAddressType
            SYNTAX      INTEGER { ipv4(1) }
            DESCRIPTION "VXSM only supports 'ipv4' type."

        VARIATION       cXgcpMsgStatsMgcIPAddress
            SYNTAX      OCTET STRING (SIZE(4))
            DESCRIPTION "VXSM only supports 'InetAddressIPv4' format."

        VARIATION       cXgcpMediaGwMaxExpTimeout
            SYNTAX      Integer32 (1..10000)
            DEFVAL      { 4000 }
            DESCRIPTION "The supported range is 1 to 10000."

        VARIATION       cXgcpMediaGwMaxMsgSize
            SYNTAX      Integer32 (512..60000)
            DEFVAL      { 60000 }
            DESCRIPTION "The valid range is 512 to 60000.
                         The initial value is 60000."

        VARIATION       cXgcpMediaGwRequestRetries
            ACCESS      not-implemented
            DESCRIPTION "not supported in VXSM."

        VARIATION       cXgcpMediaGwRequestRetryMethod
            ACCESS      not-implemented
            DESCRIPTION "not supported in VXSM."

        VARIATION       cXgcpMediaGwRestartMwd
            ACCESS      not-implemented
            DESCRIPTION "not supported in VXSM."

        VARIATION       cXgcpMediaGwRestartDelay
            ACCESS      not-implemented
            DESCRIPTION "not supported in VXSM."

        VARIATION       cXgcpMediaGwLongDurTimer
            SYNTAX      Integer32 (1..65535)
            DESCRIPTION "The valid range is 1 to 65535."

        VARIATION       cXgcpMediaGwProfile
            SYNTAX      CCallControlProfileIndexOrZero (0..25)
            DESCRIPTION "The valid range is 0 to 25."

        VARIATION       cXgcpMediaGwConfiguredPackages
            SYNTAX      BITS {
                             packageG     (2),
                             packageD     (3),
                             packageT     (5),
                             packageMO    (15),
                             packageIT    (18),
                             packageMT    (19),
                             packageFXR   (23),
                             packageBA    (24)
                        }
            DESCRIPTION "Limited data values are supported."

    ::= { ciscoXgcpCapability 5 }

ciscoXgcpCapabilityV12R03AS5000 AGENT-CAPABILITIES

PRODUCT-RELEASE "Cisco IOS 12.3"
STATUS          obsolete -- superseded by ciscoXgcpCapabilityV12R04AS5000
DESCRIPTION     "Cisco XGCP MIB capabilities"

    SUPPORTS        CISCO-XGCP-MIB
    INCLUDES        {
                      cXgcpMgcConfigGroup,
                      cXgcpMediaGwGroup,
                      cXgcpMsgStatsGroup,
                      cXgcpStatsGroup,
                      cXgcpConnectionGroup
                    }

    VARIATION       cXgcpMgcConfigMgcGrpNum
    SYNTAX          CMgcGroupIndexOrZero (0)
    ACCESS          read-only
    DESCRIPTION     "IOS does not allow to associate any MGC group."

    VARIATION       cXgcpMgcConfigAddrType
    SYNTAX          InetAddressType { unknown(0), ipv4(1), dns(16) }
    ACCESS          read-only
    DESCRIPTION     "IOS supports only IPV4 addresses and DNS names as
                     Media Gateway Controller address."

    VARIATION       cXgcpMgcConfigAddress
    ACCESS          read-only
    DESCRIPTION     "Write not implemented."

    VARIATION       cXgcpMgcConfigProtocolIndex
    ACCESS          not-implemented
    DESCRIPTION    "This object is currently not implemented."

    VARIATION       cXgcpMgcConfigGatewayUdpPort
    SYNTAX          CiscoPort (1025..65535)
    ACCESS          read-only
    DESCRIPTION     "IOS does not allow to set the MGCP port to
                     well-known ports, 0 to 1024."

    VARIATION       cXgcpMediaGwRequestTimeOut
    ACCESS          read-only
    DESCRIPTION     "Write not implemented."

    VARIATION       cXgcpMediaGwRequestRetries
    ACCESS          not-implemented
    DESCRIPTION     "This object is currently not implemented."

    VARIATION       cXgcpMediaGwRequestRetryMethod
    SYNTAX          CXgcpRetryMethod { resetTimerForEndpoint (4) }
    ACCESS          read-only
    DESCRIPTION     "IOS supports only resetTimerForEndpoint method."

    VARIATION       cXgcpMediaGwMaxExpTimeout
    ACCESS          read-only
    DESCRIPTION     "Write not implemented."

    VARIATION       cXgcpMediaGwRestartMwd
    ACCESS          read-only
    DESCRIPTION     "Write not implemented."

    VARIATION       cXgcpMediaGwRestartDelay
    ACCESS          read-only
    DESCRIPTION     "Write not implemented."

    VARIATION       cXgcpMediaGwDefaultPackage
    SYNTAX          INTEGER
                    {
                       packageG(2), packageD(3), packageM(4),
                       packageT(5), packageL(6), packageR(8),
                       packageN(9), packageA(10),packageS(11),
                       packageMS(13), packageDT(14), packageMO(15),
                       packageRES(16),  packageIT(18), packageMT(19),
                       packageFXR(23)
                    }
    ACCESS          read-only
    DEFVAL          { packageT }
    DESCRIPTION     "Write not implemented. All packages not supported.
                     Default value is Trunk Package."

    VARIATION       cXgcpMediaGwSupportedPackages
    SYNTAX          BITS
                    {
                      packageG(2), packageD(3), packageM(4),
                      packageT(5), packageL(6), packageR(8),
                      packageN(9), packageA(10), packageS(11),
                      packageMS(13),  packageDT(14), packageMO(15),
                      packageRES(16), packageIT(18), packageMT(19),
                      packageFXR(23)
                    }
    DESCRIPTION     "IOS supports only Dont care, Generic, DTMF, Trunk
                     Line, RTP, NAS, Announcement Server, Script,
                     MF CAS, DTMF CAS, MO, RES, IT, MT and FAX
                     packages"

    VARIATION       cXgcpMediaGwSimpleSdpEnabled
    ACCESS          read-only
    DESCRIPTION     "Write not implemented."

    VARIATION       cXgcpMediaGwAckSdpEnabled
    ACCESS          read-only
    DESCRIPTION     "Write not implemented."

    VARIATION       cXgcpMediaGwUndottedNotation
    ACCESS          read-only
    DESCRIPTION     "Write not implemented."

    VARIATION       cXgcpMediaGwQuarantineProcess
    ACCESS          read-only
    DESCRIPTION     "Write not implemented."

    VARIATION       cXgcpMediaGwQuarantineLoop
    ACCESS          read-only
    DESCRIPTION     "Write not implemented."

    VARIATION       cXgcpMediaGwQuarantinePersist
    ACCESS          read-only
    DESCRIPTION     "Write not implemented."

    VARIATION       cXgcpMediaGwPiggybackMsg
    ACCESS          read-only
    DESCRIPTION     "Write not implemented."

    VARIATION       cXgcpMediaGwMaxMsgSize
    SYNTAX          Integer32 (0)
    ACCESS          read-only
    DESCRIPTION     "IOS does not impose any limit on the maximum size
                     of the message."

    VARIATION       cXgcpMediaGwLastFailMgcAddrType
    ACCESS          not-implemented
    DESCRIPTION     "This object is currently not implemented."

    VARIATION       cXgcpMediaGwLastFailMgcAddr
    ACCESS          not-implemented
    DESCRIPTION     "This object is currently not implemented."

    VARIATION       cXgcpMediaGwDtmfRelay
    ACCESS          not-implemented
    DESCRIPTION     "This object is currently not implemented."

    VARIATION       cXgcpMsgStatsMgcIPAddressType
    SYNTAX          InetAddressType { unknown(0), ipv4(1), dns(16) }
    DESCRIPTION     "IOS supports only IPV4 addresses and DNS names as
                     Media Gateway Controller address."

    VARIATION       cXgcpMsgStatsIncompleteMessages
    ACCESS          not-implemented
    DESCRIPTION     "This object is currently not implemented."

    VARIATION       cXgcpMediaGwCaleaEnabled
    ACCESS          not-implemented
    DESCRIPTION     "This object is currently not implemented."

    VARIATION       cXgcpMediaGwConfiguredPackages
    ACCESS          not-implemented
    DESCRIPTION     "This object is currently not implemented."

    VARIATION       cXgcpMediaGwConnOosRsipBehavior
    ACCESS          not-implemented
    DESCRIPTION     "This object is currently not implemented."

    VARIATION       cXgcpMediaGwLongDurTimer
    ACCESS          not-implemented
    DESCRIPTION     "This object is currently not implemented."

    VARIATION       cXgcpMediaGwProfile
    ACCESS          not-implemented
    DESCRIPTION     "This object is currently not implemented."

    VARIATION       cXgcpMediaGwAnnexabSdpEnabled
    ACCESS          not-implemented
    DESCRIPTION     "This object is currently not implemented."

    ::= { ciscoXgcpCapability 6 }

ciscoXgcpCapabilityV12R04AS5000 AGENT-CAPABILITIES

PRODUCT-RELEASE "Cisco IOS 12.4"
STATUS          current
DESCRIPTION     "Cisco XGCP MIB capabilities"

    SUPPORTS        CISCO-XGCP-MIB
    INCLUDES        {
                      cXgcpMgcConfigGroup,
                      cXgcpMediaGwGroup,
                      cXgcpMsgStatsGroup,
                      cXgcpStatsGroup,
                      cXgcpConnectionGroup
                    }

    VARIATION       cXgcpMgcConfigMgcGrpNum
    SYNTAX          CMgcGroupIndexOrZero (0)
    ACCESS          read-only
    DESCRIPTION     "IOS does not allow to associate any MGC group."

    VARIATION       cXgcpMgcConfigAddrType
    SYNTAX          InetAddressType { unknown(0), ipv4(1), dns(16) }
    ACCESS          read-only
    DESCRIPTION     "IOS supports only IPV4 addresses and DNS names as
                     Media Gateway Controller address."

    VARIATION       cXgcpMgcConfigAddress
    ACCESS          read-only
    DESCRIPTION     "Write not implemented."

    VARIATION       cXgcpMgcConfigProtocolIndex
    ACCESS          not-implemented
    DESCRIPTION    "This object is currently not implemented."

    VARIATION       cXgcpMgcConfigGatewayUdpPort
    SYNTAX          CiscoPort (1025..65535)
    ACCESS          read-only
    DESCRIPTION     "IOS does not allow to set the MGCP port to
                     well-known ports, 0 to 1024."

    VARIATION       cXgcpMediaGwRequestTimeOut
    ACCESS          read-only
    DESCRIPTION     "Write not implemented."

    VARIATION       cXgcpMediaGwRequestRetries
    ACCESS          not-implemented
    DESCRIPTION     "This object is currently not implemented."

    VARIATION       cXgcpMediaGwRequestRetryMethod
    SYNTAX          CXgcpRetryMethod { resetTimerForEndpoint (4) }
    ACCESS          read-only
    DESCRIPTION     "IOS supports only resetTimerForEndpoint method."

    VARIATION       cXgcpMediaGwMaxExpTimeout
    ACCESS          read-only
    DESCRIPTION     "Write not implemented."

    VARIATION       cXgcpMediaGwRestartMwd
    ACCESS          read-only
    DESCRIPTION     "Write not implemented."

    VARIATION       cXgcpMediaGwRestartDelay
    ACCESS          read-only
    DESCRIPTION     "Write not implemented."

    VARIATION       cXgcpMediaGwDefaultPackage
    SYNTAX          INTEGER
                    {
                       packageG(2), packageD(3), packageM(4),
                       packageT(5), packageR(8), packageMS(13), 
                       packageN(9), packageA(10),packageS(11),
                       packageDT(14), packageMO(15), packageRES(16),
                       packageIT(18), packageFXR(23), packageMD(25), 
                       packageNAS(26)
                    }
    ACCESS          read-only
    DEFVAL          { packageT }
    DESCRIPTION     "AS5000 supports G, D, M, T, R, N, A, S, RES,
                     IT, FXR, NAS, MS, DT, MO, MD packages"

    VARIATION       cXgcpMediaGwSupportedPackages
    SYNTAX          BITS
                    {
                       packageG(2), packageD(3), packageM(4),
                       packageT(5), packageR(8), packageMS(13), 
                       packageN(9), packageA(10),packageS(11),
                       packageDT(14), packageMO(15), packageRES(16),
                       packageIT(18), packageFXR(23), packageMD(25),  
                       packageNAS(26)

                    }
    DESCRIPTION     "AS5000 supports G, D, M, T, R, N, A, S, RES,
                     IT, FXR, NAS, MS, DT, MO, MD packages"

    VARIATION       cXgcpMediaGwSimpleSdpEnabled
    ACCESS          read-only
    DESCRIPTION     "Write not implemented."

    VARIATION       cXgcpMediaGwAckSdpEnabled
    ACCESS          read-only
    DESCRIPTION     "Write not implemented."

    VARIATION       cXgcpMediaGwUndottedNotation
    ACCESS          read-only
    DESCRIPTION     "Write not implemented."

    VARIATION       cXgcpMediaGwQuarantineProcess
    ACCESS          read-only
    DESCRIPTION     "Write not implemented."

    VARIATION       cXgcpMediaGwQuarantineLoop
    ACCESS          read-only
    DESCRIPTION     "Write not implemented."

    VARIATION       cXgcpMediaGwQuarantinePersist
    ACCESS          read-only
    DESCRIPTION     "Write not implemented."

    VARIATION       cXgcpMediaGwPiggybackMsg
    ACCESS          read-only
    DESCRIPTION     "Write not implemented."

    VARIATION       cXgcpMediaGwMaxMsgSize
    SYNTAX          Integer32 (0)
    ACCESS          read-only
    DESCRIPTION     "IOS does not impose any limit on the maximum size
                     of the message."

    VARIATION       cXgcpMediaGwLastFailMgcAddrType
    ACCESS          not-implemented
    DESCRIPTION     "This object is currently not implemented."

    VARIATION       cXgcpMediaGwLastFailMgcAddr
    ACCESS          not-implemented
    DESCRIPTION     "This object is currently not implemented."

    VARIATION       cXgcpMediaGwDtmfRelay
    ACCESS          not-implemented
    DESCRIPTION     "This object is currently not implemented."

    VARIATION       cXgcpMsgStatsMgcIPAddressType
    SYNTAX          InetAddressType { unknown(0), ipv4(1), dns(16) }
    DESCRIPTION     "IOS supports only IPV4 addresses and DNS names as
                     Media Gateway Controller address."

    VARIATION       cXgcpMsgStatsIncompleteMessages
    ACCESS          not-implemented
    DESCRIPTION     "This object is currently not implemented."

    VARIATION       cXgcpMediaGwCaleaEnabled
    ACCESS          not-implemented
    DESCRIPTION     "This object is currently not implemented."

    VARIATION       cXgcpMediaGwConfiguredPackages
    ACCESS          not-implemented
    DESCRIPTION     "This object is currently not implemented."

    VARIATION       cXgcpMediaGwConnOosRsipBehavior
    ACCESS          not-implemented
    DESCRIPTION     "This object is currently not implemented."

    VARIATION       cXgcpMediaGwLongDurTimer
    ACCESS          not-implemented
    DESCRIPTION     "This object is currently not implemented."

    VARIATION       cXgcpMediaGwProfile
    ACCESS          not-implemented
    DESCRIPTION     "This object is currently not implemented."

    VARIATION       cXgcpMediaGwAnnexabSdpEnabled
    ACCESS          not-implemented
    DESCRIPTION     "This object is currently not implemented."

    ::= { ciscoXgcpCapability 7 }

END
