-- *****************************************************************
-- CISCO-TELEPRESENCE-CALL-CAPABILITY.my:
-- AGENT-CAPABILITIES for the CISCO-TELEPRESENCE-CALL-MIB
--   
-- Copyright (c) 2008 - 2011 by Cisco Systems Inc.
-- All rights reserved.
--   
-- Nov 2008, Connie Chan
--   
-- ***************************************************************

CISCO-TELEPRESENCE-CALL-CAPABILITY DEFINITIONS ::= BEGIN

IMPORTS
    MODULE-IDENTITY,
    Unsigned32
        FROM SNMPv2-SMI
    AGENT-CAPABILITIES
        FROM SNMPv2-CONF
    ciscoAgentCapability
        FROM CISCO-SMI;


ciscoTelepresenceCallCapability MODULE-IDENTITY
    LAST-UPDATED    "201102020000Z"
    ORGANIZATION    "Cisco Systems, Inc."
    CONTACT-INFO
            "Cisco Systems
            Customer Service

            Postal: 170 W Tasman Drive
            San Jose, CA  95134
            USA

            Tel: +1 800 553-NETS

            E-mail: tsbu-snmp-dev@cisco.com"
    DESCRIPTION
        "Agent capabilities for CISCO-TELEPRESENCE-CALL-MIB"
    REVISION        "201102020000Z"
    DESCRIPTION
        "Added capability for Cisco Telepresence System (CTS) 1.7.0."
    REVISION        "200811300000Z"
    DESCRIPTION
        "Initial version of this MIB module."
    ::= { ciscoAgentCapability 577 }



ciscoTelepresenceCallCapabilityCTSV150 AGENT-CAPABILITIES
    PRODUCT-RELEASE "Cisco TelePresence System (CTS) 1.5.0."
    STATUS          current
    DESCRIPTION
        "TELEPRESENCE CALL MIB capabilities"

    SUPPORTS        CISCO-TELEPRESENCE-CALL-MIB
    INCLUDES        {
                        ciscoTpCallConfigurationGroup,
                        ciscoTpCallInformationGroup,
                        ciscoTpCallStatisticsGroup,
                        ciscoTpCallEventHistoryGroup
                    }
    VARIATION       ctpcTxIDRPackets
    ACCESS          not-implemented
    DESCRIPTION
        "Not supported."

    VARIATION       ctpcTxShapingWindow
    ACCESS          not-implemented
    DESCRIPTION
        "Not supported."

    VARIATION       ctpcRxIDRPackets
    ACCESS          not-implemented
    DESCRIPTION
        "Not supported."

    VARIATION       ctpcRxShapingWindow
    ACCESS          not-implemented
    DESCRIPTION
        "Not supported."

    VARIATION       ctpcStatEventHistTableSize
    SYNTAX          Unsigned32 (0)
    ACCESS          read-only
    DESCRIPTION
        "Default to zero. Write operation is not supported."

    VARIATION       ctpcStatEventMonObjectInst
    ACCESS          not-implemented
    DESCRIPTION
        "Not supported."

    VARIATION       ctpcStatEventCrossedValue
    ACCESS          not-implemented
    DESCRIPTION
        "Not supported."

    VARIATION       ctpcStatEventCrossedType
    ACCESS          not-implemented
    DESCRIPTION
        "Not supported."

    VARIATION       ctpcStatEventTimeStamp
    ACCESS          not-implemented
    DESCRIPTION
        "Not supported."

    ::= { ciscoTelepresenceCallCapability 1 }

ciscoTelepresenceCallCapabilityCTSV170 AGENT-CAPABILITIES
    PRODUCT-RELEASE "Cisco TelePresence System (CTS) 1.7.0."
    STATUS          current
    DESCRIPTION
        "TELEPRESENCE CALL MIB capabilities"

    SUPPORTS        CISCO-TELEPRESENCE-CALL-MIB
    INCLUDES        {
                        ciscoTpCallConfigurationGroup,
                        ciscoTpCallInformationGroup,
                        ciscoTpCallStatisticsGroup,
                        ciscoTpCallEventHistoryGroup,
                        ciscoTpCallMgmtSysConnEventHistGroup,
                        ciscoTpCallInformationGroupSup1,
                        ciscoTpCallStatisticsGroupSup1,
                        ciscoTpCallNotificationGroupRev1
                    }
    VARIATION       ctpcTxIDRPackets
    ACCESS          not-implemented
    DESCRIPTION
        "Not supported."

    VARIATION       ctpcTxShapingWindow
    ACCESS          not-implemented
    DESCRIPTION
        "Not supported."

    VARIATION       ctpcRxIDRPackets
    ACCESS          not-implemented
    DESCRIPTION
        "Not supported."

    VARIATION       ctpcRxShapingWindow
    ACCESS          not-implemented
    DESCRIPTION
        "Not supported."

    VARIATION       ctpcStatEventHistTableSize
    SYNTAX          Unsigned32 (0)
    ACCESS          read-only
    DESCRIPTION
        "Default to zero. Write operation is not supported."

    VARIATION       ctpcStatEventMonObjectInst
    ACCESS          not-implemented
    DESCRIPTION
        "Not supported."

    VARIATION       ctpcStatEventCrossedValue
    ACCESS          not-implemented
    DESCRIPTION
        "Not supported."

    VARIATION       ctpcStatEventCrossedType
    ACCESS          not-implemented
    DESCRIPTION
        "Not supported."

    VARIATION       ctpcStatEventTimeStamp
    ACCESS          not-implemented
    DESCRIPTION
        "Not supported."

    VARIATION       ctpcMgmtSysConnEventHistTableSize
    SYNTAX          Unsigned32 (0)
    ACCESS          read-only
    DESCRIPTION
        "Default to zero. Write operation is not supported."

    VARIATION       ctpcMgmtSysConnEventStatus
    ACCESS          not-implemented
    DESCRIPTION
        "Not supported."

    VARIATION       ctpcMgmtSysConnEventSIPRespCode
    ACCESS          not-implemented
    DESCRIPTION
        "Not supported."

    VARIATION       ctpcMgmtSysConnEventTimeStamp
    ACCESS          not-implemented
    DESCRIPTION
        "Not supported."

    VARIATION       ctpcStatEventTimeStamp
    ACCESS          not-implemented
    DESCRIPTION
        "Not supported."

    ::= { ciscoTelepresenceCallCapability 2 }

END
