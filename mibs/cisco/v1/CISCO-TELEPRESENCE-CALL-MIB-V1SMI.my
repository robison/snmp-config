-- MIB file created 08-Nov-2012 14:40:37, by
--   SMICng version 2.2.11-beta(PRO)(Solaris), January 20, 2001. Enterprise key cisco.com

CISCO-TELEPRESENCE-CALL-MIB DEFINITIONS ::= BEGIN

-- From file: "CISCO-TELEPRESENCE-CALL-MIB.my"
-- Compile options "4 7 F H N W 03 06 0B 0G 0N 0T"

IMPORTS
    RowStatus, DisplayString, TruthValue, DateAndTime, 
    VariablePointer
            FROM SNMPv2-TC-v1
    SnmpAdminString
            FROM SNMP-FRAMEWORK-MIB
    Dscp
            FROM DIFFSERV-DSCP-TC
    InetAddress, InetAddressType
            FROM INET-ADDRESS-MIB
    QosLayer2Cos
            FROM CISCO-QOS-PIB-MIB
    Unsigned64
            FROM CISCO-TC
    ciscoMgmt
            FROM CISCO-SMI
    Gauge, TimeTicks, Counter
            FROM RFC1155-SMI
    OBJECT-TYPE
            FROM RFC-1212
    TRAP-TYPE
            FROM RFC-1215;

ciscoTelepresenceCallMIB OBJECT IDENTIFIER ::= { ciscoMgmt 644 }
-- MODULE-IDENTITY
--  LastUpdated
--    201211080000Z
--  OrgName
--    Cisco Systems, Inc.
--  ContactInfo
--    Cisco Systems
--    Customer Service
--    
--    Postal: 170 W Tasman Drive
--    San Jose, CA  95134
--    USA
--    
--    Tel: +1 800 553-NETS
--    
--    E-mail: tsbu-snmp-dev@cisco.com
--  Descr
--    The MIB module defines the managed objects for
--    Telepresence calls.
--    
--    Telepresence refers to a set of technologies which 
--    allow a person to feel as if they were present, to give 
--    the appearance that they were present, or to have an 
--    effect, at a location other than their true location.
--    
--    Telepresence call is an audio-video call; however, some 
--    Telepresence systems also support audio addin call.
--    
--    Different security levels are supported in some Telepresence
--    systems; security level may be specified from call management 
--    system.
--    
--    Some Telepresence systems support Telepresence meeting, the 
--    agent of the corresponding systems may also support
--    CISCO-TELEPRESENCE-MEETING-MIB.
--  RevDate
--    201211080000Z
--  RevDescr
--    Added ctpcExtNumberMask to ctpcLocalDirNumTable.
--  RevDate
--    201204200000Z
--  RevDescr
--    Added ctpcTxDscpTelepresenceConfigured, and
--    ctpcTxDscpAudioConfigured to ctpcInfoObjects. 
--    Added ctpcRxDscpCurrent, ctpcRxDscpPrevious, 
--    ctpcRxCoSCurrent, ctpcRxCoSPrevious, to 
--    ctpcStatStreamTypeTable.
--    Added ctpcTxCallBitRate, ctpcTxPeriodBitRate,
--    ctpcRxCallBitRate, ctpcRxPeriodBitRate,
--    ctpcRxMaxPeriodLostPackets, ctpcRxMaxCallLostPackets,
--    ctpcRxMaxCallLostPacketsRecTime to ctpcStatStreamSourceTable.
--  RevDate
--    201201110000Z
--  RevDescr
--    Added 'content' enum to CtpcStreamMediaType to support BFCP protocol or
--    other standard protocols in the future.
--  RevDate
--    201105160000Z
--  RevDescr
--    Updated CtpcCallTerminationCode.
--  RevDate
--    201102040000Z
--  RevDescr
--    Updated CtpcStateCode.
--  RevDate
--    201101310000Z
--  RevDescr
--    Added ctpcCalLTermReason, ctpcRxVideoHorzPixels,
--    ctpcRxVideoVertPixels, ctpcTxVideoHorzPixels, 
--    ctpcTxVideoVertPixels, ctpcMediaSrcPort, ctpcMediaDestPort.
--    
--    Clarified the definition of ctpcAvgPeriodJitter, 
--    ctpcRxMaxPeriodJitter, ctpcRxMaxCallJitter.
--    Enhanced CtpcStateCode and CtpcCodecType.
--  RevDate
--    200910210000Z
--  RevDescr
--    Added ctpcAttributes, ctpcRemoteDeviceType, ctpcTxCodec,
--    ctpcTxFrameRate, ctpcRxCodec, ctpcRxFrameRate, 
--    ctpcMgmtSysConnStatus, ctpcMgmtSysSIPRespCode and 
--    ctpcMgmtSysConnEventHistoryTable. Enhanced CtpcStateCode and
--    CtpcStreamSourceType.
--  RevDate
--    200809170000Z
--  RevDescr
--    Updated the description on default value setting for the
--    objects ctpcStatRisingThreshold and ctpcStatFallingThreshold.
--    Added new enumeration 'unknown' to ctpcType and ctpcDirection.
--    Updated the unit of ctpcTxTotalBytes and ctpcTxTotalPackets.
--  RevDate
--    200801230000Z
--  RevDescr
--    Updated the description on CtpcEntry.
--  RevDate
--    200712280000Z
--  RevDescr
--    Initial version of this MIB module.

ciscoTelepresenceCallMIBNotifs OBJECT IDENTIFIER ::= { ciscoTelepresenceCallMIB 0 }
ciscoTelepresenceCallMIBObjects OBJECT IDENTIFIER ::= { ciscoTelepresenceCallMIB 1 }
ciscoTelepresenceCallMIBConform OBJECT IDENTIFIER ::= { ciscoTelepresenceCallMIB 2 }
ctpcObjects     OBJECT IDENTIFIER ::= { ciscoTelepresenceCallMIBObjects 1 }
ctpcInfoObjects OBJECT IDENTIFIER ::= { ciscoTelepresenceCallMIBObjects 2 }
ctpcStatMonitorObjects OBJECT IDENTIFIER ::= { ciscoTelepresenceCallMIBObjects 3 }
ctpcStatObjects OBJECT IDENTIFIER ::= { ciscoTelepresenceCallMIBObjects 4 }
ctpcStatEventHistory OBJECT IDENTIFIER ::= { ciscoTelepresenceCallMIBObjects 5 }
ctpcMgmtSysConnEventHistory OBJECT IDENTIFIER ::= { ciscoTelepresenceCallMIBObjects 6 }
ciscoTpCallMIBCompliances OBJECT IDENTIFIER ::= { ciscoTelepresenceCallMIBConform 1 }
ciscoTpCallMIBGroups OBJECT IDENTIFIER ::= { ciscoTelepresenceCallMIBConform 2 }

CtpcE164Address ::= OCTET STRING(SIZE(1..32))
-- TEXTUAL-CONVENTION
--  DspHint
--    32t
--  Status
--    mandatory
--  Descr
--    A UTF-8 string limited to the character set defined for
--    E.164, '0123456789*#,<quote>'.
--    Note that <quote> represents the double quote which
--    cannot be contained in a SMI description clause.
--  Refer
--    ITU-T E.164

CtpcStreamMediaType ::= INTEGER {
        video(1),
        audio(2),
        content(3)
        }
-- TEXTUAL-CONVENTION
--  Status
--    mandatory
--  Descr
--    This textual convention identifies a call stream type. A
--    Telepresence call has two media streams, video and audio while 
--    an audio add-in call only has one media stream, audio.
--    
--       video (1) == Video stream of a call.
--       audio (2) == Audio stream of a call.
--       content(3)== Content stream of a call, such as presentation

CtpcStreamSourceType ::= INTEGER {
        secCodec1(1),
        priCodec(2),
        secCodec2(3),
        auxiliary1(4),
        secLegacy1(5),
        priLegacy(6),
        secLegacy2(7),
        auxiliary2(8)
        }
-- TEXTUAL-CONVENTION
--  Status
--    mandatory
--  Descr
--    This textual convention identifies the stream source of a call.
--    secCodec1   (1) == First secondary CODEC stream
--    priCodec    (2) == Primary CODEC stream
--    secCodec2   (3) == Second secondary CODEC stream
--    auxiliary1  (4) == First auxiliary stream like presentation 
--                       stream.
--    secLegacy1  (5) == Legacy stream generated by first
--                       secondary CODEC for legacy system.
--    priLegacy   (6) == Legacy stream generated by Primary CODEC 
--                       for legacy system.
--    secLegacy2  (7) == Legacy stream generated by second
--                       secondary CODEC for legacy system.
--    auxiliary2  (8) == Second auxiliary stream.

CtpcStateCode ::= INTEGER {
        unknown(1),
        other(2),
        noMgmtSysConn(3),
        noDialTone(4),
        invalidNumber(5),
        ringing(6),
        noAnswer(7),
        inProgress(8),
        remoteHold(9),
        shareLineActive(10),
        inLocalConference(11),
        terminatedbyError(12),
        localHold(13),
        terminatedNormally(14),
        answer(15),
        resume(16),
        busy(17),
        pause(18),
        playback(19),
        recording(20)
        }
-- TEXTUAL-CONVENTION
--  Status
--    mandatory
--  Descr
--    The textual convention identifies a call state.
--    unknown            (1)  == 
--        The system does not know what state that the call is in.
--    other              (2)  == 
--        The call is in a state not listed.
--    noMgmtSysConn      (3)  == 
--        The call cannot be dialed out due to no call
--        management system connection. It is applicable only
--        if the system is in 'mgmtSys' mode.
--    noDialTone         (4)  == 
--        The call cannot be dialed out due to no line is 
--        available.
--    invalidNumber      (5)  == 
--        The directory number of the remote party is invalid.
--    ringing            (6)  == 
--        The call is waiting to be answered.
--    noAnswer           (7)  == 
--        The call is not answered.        
--    inProgress         (8)  == 
--        The call is in progress. 
--    remoteHold         (9) == 
--        The call is on hold by remote party.
--    shareLineActive    (10) == 
--        The call is being picked up by other share line device.
--    inLocalConference  (11) == 
--        The call is in local conference mode.
--    terminatedByError  (12) == 
--        The call is terminated because of error.
--    localHold          (13)  ==
--        The call is on hold by local party.
--    terminatedNormally (14) ==
--        The call is terminated normally.
--    answer             (15) ==
--        Answer an incoming call.
--    resume             (16) ==
--        Resume a call from local hold.
--    busy               (17) ==
--        The call is not answered due to remote busy.
--    pause              (18) ==
--        Put the call in pause mode, no video and audio streams
--        will be received.
--    playback           (19) ==
--        The call is in playback state.
--    recording          (20) ==
--        The call is being recorded.

CtpcStatMonitoredAttribute ::= INTEGER {
        latency(1),
        jitter(2),
        packetLoss(3),
        authFailurePacket(4)
        }
-- TEXTUAL-CONVENTION
--  Status
--    mandatory
--  Descr
--    The textual convention identifies the monitoring type for a
--    Telepresence call.
--       latency           (1) == 
--            Round trip latency measurement.
--       jitter            (2) == 
--            Jitter of incoming and/or outgoing frames.
--       packetLoss        (3) == 
--            Percentage of packet loss for the incoming and/or
--            outgoing packets.
--       authFailurePacket (4) == 
--            Number of packets which has Secured Real-Time
--            Protocol (SRTP) or Secured Real-Time Control
--            Protocol (SRTCP) authentication failure.

CtpcStatMonitoredAttributeUnit ::= INTEGER {
        milliseconds(1),
        micropercent(2),
        packets(3)
        }
-- TEXTUAL-CONVENTION
--  Status
--    mandatory
--  Descr
--    The textual convention identifies a Telepresence call
--    monitoring type's measuring unit which is milliseconds, 
--    micropercent (10^-6 percent) or number of packets.

CtpcStatAlarmMode ::= INTEGER {
        risingAlarm(1),
        fallingAlarm(2),
        risingOrFallingAlarm(3)
        }
-- TEXTUAL-CONVENTION
--  Status
--    mandatory
--  Descr
--    The textual convention identifies the monitoring alarm mode.
--    risingAlarm          (1) == 
--        Alarm will be generated if first sample is greater 
--        than or equal to rising threshold.
--    fallingAlarm         (2) == 
--        Alarm will be generated if first sample is less         
--        than or equal to falling threshold.
--    risingOrFallingAlarm (3) == 
--        Alarm will be generated if first sample is greater         
--        than or equal to rising threshold or less than or
--        equal to falling threshold.

CtpcStatThreshCrossedType ::= INTEGER {
        risingThreshold(1),
        fallingThreshold(2)
        }
-- TEXTUAL-CONVENTION
--  Status
--    mandatory
--  Descr
--    The textual convention identifies the monitoring threshold
--    cross type.
--        risingThreshold  (1) == 
--            The sample data has crossed the rising threshold.
--        fallingThreshold (2) == 
--            The sample data has crossed the falling threshold.

CtpcAttributes ::= OCTET STRING(SIZE(1..2))
        -- BITS are:
        --   interop(0)
        --   highDefinitionInterop(1)
        --   webEx(2)
        --   schedule(3)
        --   satellite(4)
        --   t1(5)
        --   liveDesk(6)
-- TEXTUAL-CONVENTION
--  Status
--    mandatory
--  Descr
--    The textual convention identifies the attributes or
--    characteristics of a call.
--        interop   (0) == 
--            The call involves at least one interop party.
--        highDefinitionInterop (1) == 
--            The call involves at least one high definition interop
--            party.
--        webEx     (2) == 
--            The call involves at least one WebEx party. 
--        schedule  (3) == 
--            This call is a scheduled call.
--        satellite (4) == 
--            This call is going through satellite connection.
--        t1        (5) ==
--            This call is going through T1 connection.
--        liveDesk  (6) ==
--            This call is calling to live desk.

CtpcRemoteDeviceType ::= INTEGER {
        unknown(1),
        other(2),
        audioDevice(3),
        videoLegacyDevice(4),
        highDefinitionLegacyDevice(5),
        singleTelepresence(6),
        tripleTelepresence(7),
        telepresenceMultipointSwitch(8),
        telepresenceRecordingServer(9),
        telepresenceTranscodingDevice(10)
        }
-- TEXTUAL-CONVENTION
--  Status
--    mandatory
--  Descr
--    The textual convention identifies the remote device type of
--    a call.
--    
--        unknown                      (1)  ==
--            The remote device type is not known.
--        other                        (2)  == 
--            The remote device type is not listed.
--        audioDevice                  (3)  ==
--            Audio device.
--        videoLegacyDevice            (4)  ==
--            Video device which is sending legacy stream.
--        highDefinitionLegacyDevice   (5)  == 
--            Video device which is sending high definition legacy
--            stream.
--        singleTelepresence           (6)  ==
--            Telepresence device which is sending single video
--            stream.
--        tripleTelepresence           (7)  ==
--            Telepresence device which is sending three video
--            streams.
--        telepresenceMultipointSwitch (8)  ==
--            Telepresence Multipoint Switch.
--        telepresenceRecordingServer  (9)  ==
--            Telepresence Recording Server.
--        telepresenceTranscodingDevice(10) ==
--            Telepresence Transcoding Device.

CtpcCodecType ::= INTEGER {
        unknown(1),
        other(2),
        aaclc(3),
        aacld(4),
        g711A(5),
        g711U(6),
        g722(7),
        g7221(8),
        g728(9),
        g729(10),
        h263(11),
        h264(12),
        aacldLatm(13)
        }
-- TEXTUAL-CONVENTION
--  Status
--    mandatory
--  Descr
--    The textual convention identifies the codec type of a stream.
--    unknown (1)  == Codec type is not known.
--    other   (2)  == Codec type is not listed.
--    aaclc   (3)  == Advanced Audio Coding, Low Complexity.
--    aacld   (4)  == MPEG-4 Low Delay Audio Codec.
--    g711A   (5)  == G.711 A-Law audio codec.
--    g711U   (6)  == G.711 U-Law audio codec.
--    g722    (7)  == G.722 audio codec.
--    g7221   (8)  == G.7221 audio codec.
--    g728    (9)  == G.728 audio codec.
--    g729    (10) == G.729 audio codec.
--    h263    (11) == H.263 video codec.
--    h264    (12) == H.264 video codec.
--    aacldLatm (13) == Advanced Audio Coding, Low Delay,
--                   == Low-overhead MPEG4 Audio Transport 
--                   == Multiplexing.

CtpcMgmtSysConnStatusCode ::= INTEGER {
        unknown(1),
        other(2),
        internalError(3),
        notRegister(4),
        registered(5),
        registraionFailure(6)
        }
-- TEXTUAL-CONVENTION
--  Status
--    mandatory
--  Descr
--    The textual convention identifies the management system
--    connection status.
--        unknown           (1) == 
--            Call management system connection status is unknown.
--        other             (2) == 
--            Call management system connection status is not listed.
--        internalError     (3) ==
--            Telepresence system has internal system error to return
--            call management system connection status.
--        notRegister       (4) == 
--            Telepresence system is not register to the
--            call management system.
--        registered        (5) == 
--            Telepresence registered to a call management system. 
--        registrationFailure (6) == 
--            Call management system registration failed.

CtpcCallTerminationCode ::= INTEGER {
        unknown(1),
        other(2),
        internalError(3),
        localDisconnected(4),
        remoteDisconnected(5),
        networkCongestion(6),
        mediaNegotiationFailure(7),
        securityConfigMismatched(8),
        incompatibleRemoteEndPt(9),
        serviceUnavailable(10),
        remoteTerminatedWithError(11)
        }
-- TEXTUAL-CONVENTION
--  Status
--    mandatory
--  Descr
--    The textual convention identifies a call termination
--    reason.
--        unknown            (1) == 
--            Call termination reason is unknown.
--        other              (2) == 
--            Call termination reason is not listed.
--        internalError      (3) == 
--            Telepresence system has internal system error to
--            return call termination reason.
--        localDisconnected  (4) == 
--            Call is terminated due to local user disconnected. 
--        remoteDisconnected (5) == 
--            Call is terminated due to remote user disconnected. 
--        networkCongestion  (6) == 
--            Call is terminated due to network congestion.
--        mediaNegotiationFailure (7) == 
--            Call is terminated due to media negotiation failure.
--        securityConfigMismatched (8) == 
--            Call is terminated due to security configuration
--            mismatched.
--        incompatibleRemoteEndPt (9) == 
--            Call is terminated due to incompatible remote end 
--            point.
--        serviceUnavailable (10) == 
--            Call cannot be routed due to service unavailable.
--        remoteTerminatedWithError (11) ==
--            Call is terminated due to remote end point termination 
--            with error.

ctpcStatNotifyEnable OBJECT-TYPE
    SYNTAX TruthValue
--    Rsyntax INTEGER {
--        true(1),
--        false(2)
--        }
    ACCESS read-write
    STATUS mandatory
    DESCRIPTION
        "This object controls generation of notifications for the
        real-time call statistics data monitoring.
        
        Call statistics monitoring threshold can be set by creating
        a corresponding ctpcStatMonitoredEntry. Notification will be
        generated based on the value of the ctpcStatStartupAlarm and
        the thresholds.
        
        When the object is 'true', the agent will generate
        notification when the monitoring threshold is crossed.
        
        When the object is 'false', the agent will not
        generate notification when the monitoring threshold is crossed."
    DEFVAL { false }
    ::= { ctpcObjects 1 }

ctpcMgmtSysConnNotifyEnable OBJECT-TYPE
    SYNTAX TruthValue
--    Rsyntax INTEGER {
--        true(1),
--        false(2)
--        }
    ACCESS read-write
    STATUS mandatory
    DESCRIPTION
        "This object controls generation of notifications for
        call management system connection state changes.
        
        When the object is 'true', the agent will generate
        notification when call management system connection state
        changes.
        
        When the object is 'false', the agent will not
        generate notification when call management system connection 
        state changes."
    DEFVAL { false }
    ::= { ctpcObjects 2 }

ctpcLocalAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object specifies the type of address contained in
        the corresponding instance of ctpcLocalAddr."
    ::= { ctpcInfoObjects 1 }

ctpcLocalAddr OBJECT-TYPE
    SYNTAX InetAddress
--    Rsyntax OCTET STRING(SIZE(0..255))
    ACCESS read-only
    STATUS mandatory
    DESCRIPTION
        "This object specifies the address of the system in the format
        given by the corresponding instance of ctpcLocalAddrType."
    ::= { ctpcInfoObjects 2 }

ctpcLocalDirNumTable OBJECT-TYPE
    SYNTAX SEQUENCE OF CtpcLocalDirNumEntry
    ACCESS not-accessible
    STATUS mandatory
    DESCRIPTION
        "A table of information about E.164 numbers assigned to the
        Telepresence system.
        
        The directory numbers usually are specified by the call 
        management system.
        
        Some Telepresence systems have only one E.164 number assigned."
    ::= { ctpcInfoObjects 3 }

ctpcLocalDirNumEntry OBJECT-TYPE
    SYNTAX CtpcLocalDirNumEntry
    ACCESS not-accessible
    STATUS mandatory
    DESCRIPTION
        "An entry containing information about one E.164 number."
    INDEX { ctpcLocalDirNumIndex }
    ::= { ctpcLocalDirNumTable 1 }

CtpcLocalDirNumEntry ::= SEQUENCE {
    ctpcLocalDirNumIndex Gauge,
    ctpcLocalDirNum CtpcE164Address,
    ctpcExtNumberMask SnmpAdminString
    }

ctpcLocalDirNumIndex OBJECT-TYPE
    SYNTAX Gauge
    ACCESS not-accessible
    STATUS mandatory
    DESCRIPTION
        "The object specifies a unique index for a local directory
        number entry associates to the system."
    ::= { ctpcLocalDirNumEntry 1 }

ctpcLocalDirNum OBJECT-TYPE
    SYNTAX CtpcE164Address
--    Rsyntax OCTET STRING(SIZE(1..32))
    ACCESS read-only
    STATUS mandatory
    DESCRIPTION
        "This object specifies the directory number of the Telepresence
        system."
    ::= { ctpcLocalDirNumEntry 2 }

ctpcExtNumberMask OBJECT-TYPE
    SYNTAX SnmpAdminString
--    Rsyntax OCTET STRING(SIZE(0..255))
    ACCESS read-only
    STATUS mandatory
    DESCRIPTION
        "This object indicates the external number mask that configured in
        the management system.  For example, if ctpcExtNumberMask is 
        configured as 9728XXXXX, and ctpcLocalDirNum is configured as 12345,
        the external caller shall see the Directory Number (DN) as 972812345"
    ::= { ctpcLocalDirNumEntry 3 }

ctpcMode OBJECT-TYPE
    SYNTAX INTEGER {
        noMgmtSys(1),
        mgmtSys(2)
        }
    ACCESS read-only
    STATUS mandatory
    DESCRIPTION
        "This object specifies the system configured call mode. It
        indicates if the call is processed by call management system  
        or not.
        
        nonMgmtSys(1) -- 
            Telepresence system that does not connect to any call
            management system such as Cisco Unified Communication
            Manager (CUCM).
        mgmtSys   (2) -- 
            Telepresence system that connects to a call management
            system.
        
        Note that some Telepresence systems support 'mgmtSys' only."
    ::= { ctpcInfoObjects 4 }

ctpcActiveMgmtSysIndex OBJECT-TYPE
    SYNTAX Gauge
    ACCESS read-only
    STATUS mandatory
    DESCRIPTION
        "This object specifies the value of ctpcMgmtSysIndex
        which the Telepresence system currently connects.
        
        If the system is in 'nonMgmtSys' mode, this object will have
        value '0'"
    ::= { ctpcInfoObjects 5 }

ctpcMgmtSysTable OBJECT-TYPE
    SYNTAX SEQUENCE OF CtpcMgmtSysEntry
    ACCESS not-accessible
    STATUS mandatory
    DESCRIPTION
        "A table of configured call management systems."
    ::= { ctpcInfoObjects 6 }

ctpcMgmtSysEntry OBJECT-TYPE
    SYNTAX CtpcMgmtSysEntry
    ACCESS not-accessible
    STATUS mandatory
    DESCRIPTION
        "An entry contains information about a call management system."
    INDEX { ctpcMgmtSysIndex }
    ::= { ctpcMgmtSysTable 1 }

CtpcMgmtSysEntry ::= SEQUENCE {
    ctpcMgmtSysIndex Gauge,
    ctpcMgmtSysAddrType InetAddressType,
    ctpcMgmtSysAddr InetAddress,
    ctpcMgmtSysConnStatus CtpcMgmtSysConnStatusCode,
    ctpcMgmtSysSIPRespCode Gauge
    }

ctpcMgmtSysIndex OBJECT-TYPE
    SYNTAX Gauge(1..4294967295)
    ACCESS not-accessible
    STATUS mandatory
    DESCRIPTION
        "This object specifies a unique index for a call
        management system entry."
    ::= { ctpcMgmtSysEntry 1 }

ctpcMgmtSysAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object specifies the type of address contained in the
        corresponding instance of ctpcMgmtSysAddr."
    ::= { ctpcMgmtSysEntry 2 }

ctpcMgmtSysAddr OBJECT-TYPE
    SYNTAX InetAddress
--    Rsyntax OCTET STRING(SIZE(0..255))
    ACCESS read-only
    STATUS mandatory
    DESCRIPTION
        "This object specifies a call management system address
        which a Telepresence system can connect to if it is in 
        'mgmtSys' mode. 
        
        It is in the format given by the corresponding  
        instance of ctpcMgmtSysAddrType."
    ::= { ctpcMgmtSysEntry 3 }

ctpcMgmtSysConnStatus OBJECT-TYPE
    SYNTAX CtpcMgmtSysConnStatusCode
--    Rsyntax INTEGER {
--        unknown(1),
--        other(2),
--        internalError(3),
--        notRegister(4),
--        registered(5),
--        registraionFailure(6)
--        }
    ACCESS read-only
    STATUS mandatory
    DESCRIPTION
        "This object specifies the last connection state
        between the Telepresence and a call management system."
    ::= { ctpcMgmtSysEntry 4 }

ctpcMgmtSysSIPRespCode OBJECT-TYPE
    SYNTAX Gauge
    ACCESS read-only
    STATUS mandatory
    DESCRIPTION
        "This object specifies the last SIP response code from
        call management system."
    REFERENCE
        "RFC 3261, section 21"
    ::= { ctpcMgmtSysEntry 5 }

ctpcTxDscpTelepresenceConfigured OBJECT-TYPE
    SYNTAX Dscp
--    Rsyntax INTEGER(0..63)
    ACCESS read-only
    STATUS mandatory
    DESCRIPTION
        "This object specifies the configured DSCP for all outgoing
        streams for a Telepresence call."
    ::= { ctpcInfoObjects 7 }

ctpcTxDscpAudioConfigured OBJECT-TYPE
    SYNTAX Dscp
--    Rsyntax INTEGER(0..63)
    ACCESS read-only
    STATUS mandatory
    DESCRIPTION
        "This object specifies the configured DSCP for outgoing streams for audio-only call."
    ::= { ctpcInfoObjects 8 }

ctpcStatMonitoredTable OBJECT-TYPE
    SYNTAX SEQUENCE OF CtpcStatMonitoredEntry
    ACCESS not-accessible
    STATUS mandatory
    DESCRIPTION
        "A table of configuration information for the monitoring of
        statistics of active Telepresence calls.
        
        The monitoring feature has a hysteresis mechanism to limit the 
        generation of events.  This mechanism generates one event as a
        threshold is crossed in the appropriate direction.  No more
        events are generated for that threshold until the opposite
        threshold is crossed."
    ::= { ctpcStatMonitorObjects 1 }

ctpcStatMonitoredEntry OBJECT-TYPE
    SYNTAX CtpcStatMonitoredEntry
    ACCESS not-accessible
    STATUS mandatory
    DESCRIPTION
        "An entry contains a particular threshold
        configuration on an attribute for a stream type.
        
        For example, if latency of video stream is configured; average 
        period latency of active Telepresence calls will be monitored.
        
        A management station wishing to monitor a call statistical 
        attribute should create the associated instance of the row 
        status.
        
        Once the appropriate instance of all the configuration objects 
        have been created, either by an explicit SNMP set request or by 
        default, the row status should be set to 'active' to initiate 
        the monitoring request. Note that only active call streams are
        monitored."
    INDEX { ctpcStatMonitoredType, ctpcStatMonitoredStreamType }
    ::= { ctpcStatMonitoredTable 1 }

CtpcStatMonitoredEntry ::= SEQUENCE {
    ctpcStatMonitoredType CtpcStatMonitoredAttribute,
    ctpcStatMonitoredStreamType INTEGER,
    ctpcStatMonitoredUnit CtpcStatMonitoredAttributeUnit,
    ctpcStatRisingThreshold Gauge,
    ctpcStatFallingThreshold Gauge,
    ctpcStatStartupAlarm CtpcStatAlarmMode,
    ctpcStatMonitoredStatus RowStatus
    }

ctpcStatMonitoredType OBJECT-TYPE
    SYNTAX CtpcStatMonitoredAttribute
--    Rsyntax INTEGER {
--        latency(1),
--        jitter(2),
--        packetLoss(3),
--        authFailurePacket(4)
--        }
    ACCESS not-accessible
    STATUS mandatory
    DESCRIPTION
        "This object specifies a statistical attribute which to be
        monitored."
    ::= { ctpcStatMonitoredEntry 1 }

ctpcStatMonitoredStreamType OBJECT-TYPE
    SYNTAX INTEGER {
        --?? enum value of zero may cause problems
--        all(0),
        video(1),
        audio(2)
        }
    ACCESS not-accessible
    STATUS mandatory
    DESCRIPTION
        "This object specifies a active Telepresence stream type
        which to be monitored.
        
        If the value of this object is 'all', all stream types are
        monitored with the corresponding ctpcStatRisingThreshold 
        and/or ctpcStatFallingThreshold for ctpcStatMonitoredType.
        
        Moreover, if this value is 'all', there cannot be another 
        row for the same value of ctpcStatMonitoredType which is either 
        'video' or 'audio'.
        
        If ctpcStatMonitoredType has value latency(1) or 
        authFailurePacket(4), this object will have value '0'.
        
        Note that some Telepresence systems may not support different 
        thresholds for different stream type."
    ::= { ctpcStatMonitoredEntry 2 }

ctpcStatMonitoredUnit OBJECT-TYPE
    SYNTAX CtpcStatMonitoredAttributeUnit
--    Rsyntax INTEGER {
--        milliseconds(1),
--        micropercent(2),
--        packets(3)
--        }
    ACCESS read-only
    STATUS mandatory
    DESCRIPTION
        "This object specifies the corresponding unit of a
        monitoring attribute.
        
        The following table lists the possible values of
        this object, given the value of the corresponding instance 
        of ctpcStatMonitoredType.
        
        ctpcStatMonitoredType      ctpcStatMonitoredUnit
        ----------------------------------------------------
        latency(1)                 milliseconds(1)
        jitter(2)                  milliseconds(1)
        packetLoss(3)              micropercent(2)
        authFailurePacket(4)       packets(3)"
    ::= { ctpcStatMonitoredEntry 3 }

ctpcStatRisingThreshold OBJECT-TYPE
    SYNTAX Gauge
    ACCESS read-write
    STATUS mandatory
    DESCRIPTION
        "This object specifies the rising threshold of a monitoring
        attribute.
        
        When the call period value of the corresponding attribute
        is greater than or equal to this threshold, a single event
        will be generated.
        A single event will also be generated if the first call period
        value of the corresponding attribute after this entry becomes
        'active' is greater than or equal to this threshold and the
        associated ctpcStatStartupAlarm is equal to risingAlarm(1) or
        risingOrFallingAlarm(3).
        
        After a rising event is generated, another such event will not
        be generated until the call period value of the corresponding
        attribute falls below this threshold and reaches the
        corresponding ctpcStatFallingThreshold.
        
        If this object is not specified when the row is created,
        default value based on the value of the corresponding
        instance of ctpcStatMonitoredType may be set by the agent.
        
        This object may not be modified if the associated
        ctpcStatMonitoredStatus object is equal to 
        active(1)."
    ::= { ctpcStatMonitoredEntry 4 }

ctpcStatFallingThreshold OBJECT-TYPE
    SYNTAX Gauge
    ACCESS read-write
    STATUS mandatory
    DESCRIPTION
        "This object specifies the falling threshold of a monitoring
        attribute.
        
        When the call period value of the corresponding attribute
        is less than or equal to this threshold, 
        [ and the value at the last sampling interval was greater than
         this threshold, ]
        a single event will be generated.
        A single event will also be generated if the first call period
        value of the corresponding attribute after this entry becomes
        'active' is less than or equal to this threshold and the
        associated ctpcStatStartupAlarm is equal to fallingAlarm(1) or
        risingOrFallingAlarm(3).
        
        After a falling event is generated, another such event will not
        be generated until the call period value of the corresponding
        attribute rises above this threshold and reaches the
        corresponding ctpcStatRisingThreshold.
        
        If this object is not specified when the row is created,
        default value based on the value of the corresponding
        instance of ctpcStatMonitoredType may be set by the agent.
        
        This object may not be modified if the associated
        ctpcStatMonitoredStatus object is equal to 
        active(1)."
    ::= { ctpcStatMonitoredEntry 5 }

ctpcStatStartupAlarm OBJECT-TYPE
    SYNTAX CtpcStatAlarmMode
--    Rsyntax INTEGER {
--        risingAlarm(1),
--        fallingAlarm(2),
--        risingOrFallingAlarm(3)
--        }
    ACCESS read-write
    STATUS mandatory
    DESCRIPTION
        "This object specifies the alarm that may be sent
        after the entry is first set to valid.
        
        If the first sample after this entry becomes valid is 
        greater than or equal to the ctpcStatRisingThreshold and 
        ctpcStatStartupAlarm is equal to risingAlarm(1) or 
        risingOrFallingAlarm(3), then a single rising alarm will be 
        generated.
        
        If the first sample after this entry becomes valid is
        less than or equal to the ctpcStatFallingThreshold and 
        ctpcStatStartupAlarm is equal to fallingAlarm(2) or
        risingOrFallingAlarm(3), then a single falling alarm will be
        generated.
        
        This object may not be modified if the associated
        ctpcStatMonitoredStatus object is equal to 
        active(1)."
    DEFVAL { risingOrFallingAlarm }
    ::= { ctpcStatMonitoredEntry 6 }

ctpcStatMonitoredStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of ctpcStatMonitoredEntry.
        Once the entry status is set to 'active', the call statistics 
        monitoring will be started.
        
        If this object is set to 'notInService' or 'destroy', the 
        monitoring will be disabled to the corresponding stream type 
        on the corresponding monitoring attribute."
    ::= { ctpcStatMonitoredEntry 7 }

ctpcStatOverallCalls OBJECT-TYPE
    SYNTAX Gauge
    ACCESS read-only
    STATUS mandatory
    DESCRIPTION
        "This object specifies total number of calls since Telepresence
        system was first in service.
        
        When it reaches a maximum value of 2^32-1
        (4294967295 decimal), it wraps around and starts increasing
        again from '1'."
    ::= { ctpcStatObjects 1 }

ctpcStatOverallCallTime OBJECT-TYPE
    SYNTAX Gauge
--  Units
--    seconds
    ACCESS read-only
    STATUS mandatory
    DESCRIPTION
        "This object specifies elapsed time of calls
        since Telepresence system was first in service.
        
        When it reaches a maximum value of 2^32-1
        (4294967295 decimal), it wraps around and starts increasing
        again from '1'."
    ::= { ctpcStatObjects 2 }

ctpcStatTotalCalls OBJECT-TYPE
    SYNTAX Gauge
    ACCESS read-only
    STATUS mandatory
    DESCRIPTION
        "This object specifies total number of calls since Telepresence
        system was last rebooted.
        
        When it reaches a maximum value of 2^32-1
        (4294967295 decimal), it wraps around and starts increasing
        again from '1'."
    ::= { ctpcStatObjects 3 }

ctpcStatTotalCallTime OBJECT-TYPE
    SYNTAX Gauge
--  Units
--    seconds
    ACCESS read-only
    STATUS mandatory
    DESCRIPTION
        "This object specifies elapsed time of calls
        since Telepresence system was last rebooted.
        
        When it reaches a maximum value of 2^32-1
        (4294967295 decimal), it wraps around and starts increasing
        again from '1'."
    ::= { ctpcStatObjects 4 }

ctpcSamplePeriod OBJECT-TYPE
    SYNTAX Gauge(10..300)
--  Units
--    seconds
    ACCESS read-write
    STATUS mandatory
    DESCRIPTION
        "This object specifies a sample period by which the following
        objects are based on:
        
            ctpcAvgPeriodLatency,
            ctpcMaxPeriodLatency,
            ctpcTxPeriodLostPackets,
            ctpcRxPeriodLostPackets,
            ctpcAvgPeriodJitter,
            ctpcMaxPeriodJitter"
    DEFVAL { 10 }
    ::= { ctpcStatObjects 5 }

ctpcTableSize OBJECT-TYPE
    SYNTAX INTEGER(-1..500)
    ACCESS read-write
    STATUS mandatory
    DESCRIPTION
        "This object specifies the maximum number of entries of the
        ctpcTable.
        
        Some agents restrict the maximum value of this object to
        be less than 500.
        
        When the capacity of the ctpcTable has reached
        the value specified by this object, then the agent 
        deletes the oldest entry in order to accommodate
        the new entry.
        
        When this object is set to '-1', ctpcTableSize will not set
        maximum entries that ctpcTable is contained.
        
        The table size in turns may be limited by the associated MIB
        such as CISCO-TELEPRESENCE-MEETING-MIB."
    DEFVAL { 10 }
    ::= { ctpcStatObjects 6 }

ctpcTableLastIndex OBJECT-TYPE
    SYNTAX Gauge(0..4294967295)
    ACCESS read-only
    STATUS mandatory
    DESCRIPTION
        "This object specifies the value of the ctpcIndex object
        corresponding to the last entry added to the table.
        
        When it reaches a maximum value of 2^32-1
        (4294967295 decimal), it wraps around and starts increasing
        again from '1'."
    ::= { ctpcStatObjects 7 }

ctpcTable OBJECT-TYPE
    SYNTAX SEQUENCE OF CtpcEntry
    ACCESS not-accessible
    STATUS mandatory
    DESCRIPTION
        "A table for Telepresence call information.
        
        After management system initialization (i.e. when 
        sysUpTime is reset to zero), this table
        records all calls until it reaches its capacity
        specifed in ctpcTableSize. Thereafter, it remains full
        by retaining the most recent calls information."
    ::= { ctpcStatObjects 8 }

ctpcEntry OBJECT-TYPE
    SYNTAX CtpcEntry
    ACCESS not-accessible
    STATUS mandatory
    DESCRIPTION
        "An entry contains information of a Telepresence supported
        call.
        
        Some Telepresence systems support both audio-video call and
        audio-addin call. 
        
        A management station wishing to create a call should create
        the associated instance of the row status and the remote 
        directory number objects.  ctpcIndex should be set to the 
        next-to-be-assigned number of ctpcTableLastIndex.
        
        An instance of ctpcRemoteDirNum is required to create
        a call.
        
        Once the appropriate instance of all the configuration
        objects have been created, the row status should be set
        to active to initiate the request. Note that this entire
        procedure may be initiated via a single set request which
        specifies a row status of createAndGo.
        
        Once a call entry has been activated, it cannot be stopped.
        
        Instance of ctpcState on the created row reports the
        latest status of the newly created call.
        
        If a Telepresence system receives a call, a unique index will 
        be chosen and an entry will be created by the agent,
        ctpcRowStatus will be set to active, and
        ctpcRemoteDirNum will be filled by agent if it is known."
    INDEX { ctpcIndex }
    ::= { ctpcTable 1 }

CtpcEntry ::= SEQUENCE {
    ctpcIndex Gauge,
    ctpcRemoteDirNum CtpcE164Address,
    ctpcLocalSIPCallId SnmpAdminString,
    ctpcTxDestAddrType InetAddressType,
    ctpcTxDestAddr InetAddress,
    ctpcStartDateAndTime DateAndTime,
    ctpcDuration Gauge,
    ctpcType INTEGER,
    ctpcSecurity INTEGER,
    ctpcDirection INTEGER,
    ctpcState CtpcStateCode,
    ctpcInitialBitRate Gauge,
    ctpcLatestBitRate Gauge,
    ctpcRowStatus RowStatus,
    ctpcAttributes CtpcAttributes,
    ctpcRemoteDevice CtpcRemoteDeviceType,
    ctpcCallTermReason CtpcCallTerminationCode
    }

ctpcIndex OBJECT-TYPE
    SYNTAX Gauge(1..4294967295)
    ACCESS not-accessible
    STATUS mandatory
    DESCRIPTION
        "This object specifies a unique identification of a call
        entry.
        
        If the chosen ctpcIndex value for the row creation
        is already in use by an existing entry, SNMP SetRequest
        to the ctpcIndex value will fail."
    ::= { ctpcEntry 1 }

ctpcRemoteDirNum OBJECT-TYPE
    SYNTAX CtpcE164Address
--    Rsyntax OCTET STRING(SIZE(1..32))
    ACCESS read-write
    STATUS mandatory
    DESCRIPTION
        "This object specifies the remote directory number of a call.
        
        Once the ctpcRowStatus is set to 'active', the
        ctpcRemoteDirNum cannot be changed."
    ::= { ctpcEntry 2 }

ctpcLocalSIPCallId OBJECT-TYPE
    SYNTAX SnmpAdminString(SIZE(0..255))
--    Rsyntax OCTET STRING(SIZE(0..255))
    ACCESS read-only
    STATUS mandatory
    DESCRIPTION
        "This object specifies the local SIP call ID."
    REFERENCE
        "RFC 3261 SIP: Session Initiation Protocol
        Section 8.1.1.4"
    ::= { ctpcEntry 3 }

ctpcTxDestAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object specifies the address type of the corresponding
        instance of ctpcTxDestAddr."
    ::= { ctpcEntry 4 }

ctpcTxDestAddr OBJECT-TYPE
    SYNTAX InetAddress
--    Rsyntax OCTET STRING(SIZE(0..255))
    ACCESS read-only
    STATUS mandatory
    DESCRIPTION
        "This object specifies the address of the media packets
        forwarded to in the format given by the corresponding instance
        of ctpcTxDestAddrType."
    ::= { ctpcEntry 5 }

ctpcStartDateAndTime OBJECT-TYPE
    SYNTAX DateAndTime
--    Rsyntax OCTET STRING(SIZE(8|11))
    ACCESS read-only
    STATUS mandatory
    DESCRIPTION
        "This object specifies the value of local date and time when
        a call is started."
    ::= { ctpcEntry 6 }

ctpcDuration OBJECT-TYPE
    SYNTAX Gauge
--  Units
--    seconds
    ACCESS read-only
    STATUS mandatory
    DESCRIPTION
        "This object specifies the elapsed time since the call
        established."
    ::= { ctpcEntry 7 }

ctpcType OBJECT-TYPE
    SYNTAX INTEGER {
        audioVideo(1),
        audioOnly(2),
        unknown(3)
        }
    ACCESS read-write
    STATUS mandatory
    DESCRIPTION
        "This object specifies the call type.
        
        audioVideo (1) -- Telepresence call.
        audioOnly  (2) -- Audio call.
        unknown    (3) -- The system cannot detect the type of a call.
        
        Some Telepresence systems only support audio-video call."
    ::= { ctpcEntry 8 }

ctpcSecurity OBJECT-TYPE
    SYNTAX INTEGER {
        nonSecured(1),
        authenticated(2),
        secured(3),
        unknown(4)
        }
    ACCESS read-write
    STATUS mandatory
    DESCRIPTION
        "This object specifies the call security level.
        
        nonSecured    (1) -- 
           Neither media packets nor signaling packets are encrypted.
        authenticated (2) -- 
           Signaling packets are authenticated and/or encrypted but
           not the media packets.
        secured       (3) -- 
           Both media packets and signaling packets are encrypted.
        unknown       (4) -- 
           Cannot detect the security state of a call."
    ::= { ctpcEntry 9 }

ctpcDirection OBJECT-TYPE
    SYNTAX INTEGER {
        incoming(1),
        outgoing(2),
        unknown(3)
        }
    ACCESS read-only
    STATUS mandatory
    DESCRIPTION
        "This object specifies the call direction.
        
        incoming (1) -- The system received a call.
        outgoing (2) -- The system initiated a call.
        unknown  (3) -- The system cannot detect the direction 
                     -- of a call."
    ::= { ctpcEntry 10 }

ctpcState OBJECT-TYPE
    SYNTAX CtpcStateCode
--    Rsyntax INTEGER {
--        unknown(1),
--        other(2),
--        noMgmtSysConn(3),
--        noDialTone(4),
--        invalidNumber(5),
--        ringing(6),
--        noAnswer(7),
--        inProgress(8),
--        remoteHold(9),
--        shareLineActive(10),
--        inLocalConference(11),
--        terminatedbyError(12),
--        localHold(13),
--        terminatedNormally(14),
--        answer(15),
--        resume(16),
--        busy(17),
--        pause(18),
--        playback(19),
--        recording(20)
--        }
    ACCESS read-write
    STATUS mandatory
    DESCRIPTION
        "This object specifies the call state."
    ::= { ctpcEntry 11 }

ctpcInitialBitRate OBJECT-TYPE
    SYNTAX Gauge
--  Units
--    kbps
    ACCESS read-write
    STATUS mandatory
    DESCRIPTION
        "This object specifies the initial bit rate of a Telepresence
        call."
    ::= { ctpcEntry 12 }

ctpcLatestBitRate OBJECT-TYPE
    SYNTAX Gauge
--  Units
--    kbps
    ACCESS read-only
    STATUS mandatory
    DESCRIPTION
        "This object specifies the current bit rate of a call.
        
        Telepresence call's bit rate may be lowered automatically 
        due to network congestion."
    ::= { ctpcEntry 13 }

ctpcRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the entry status of ctpcEntry.
        Once ctpcRowStatus is set to 'active', the call creation 
        cannot be stopped.
        
        Changing the value of this object from 'active' to
        'notInService' or 'destroy' will likely have
        consequences of call termination and/or losing the
        call statistics information.
        Thus, write access to this object is inappropriate for
        most of the Telepresence systems, and many implementations
        will choose not to support write-access for this object."
    ::= { ctpcEntry 14 }

ctpcAttributes OBJECT-TYPE
    SYNTAX CtpcAttributes
--    Rsyntax OCTET STRING(SIZE(1..2))
--         BITS are:
--           interop(0)
--           highDefinitionInterop(1)
--           webEx(2)
--           schedule(3)
--           satellite(4)
--           t1(5)
--           liveDesk(6)
    ACCESS read-only
    STATUS mandatory
    DESCRIPTION
        "This object specifies the connection mode of a call."
    ::= { ctpcEntry 15 }

ctpcRemoteDevice OBJECT-TYPE
    SYNTAX CtpcRemoteDeviceType
--    Rsyntax INTEGER {
--        unknown(1),
--        other(2),
--        audioDevice(3),
--        videoLegacyDevice(4),
--        highDefinitionLegacyDevice(5),
--        singleTelepresence(6),
--        tripleTelepresence(7),
--        telepresenceMultipointSwitch(8),
--        telepresenceRecordingServer(9),
--        telepresenceTranscodingDevice(10)
--        }
    ACCESS read-only
    STATUS mandatory
    DESCRIPTION
        "This object specifies the remote device type."
    ::= { ctpcEntry 16 }

ctpcCallTermReason OBJECT-TYPE
    SYNTAX CtpcCallTerminationCode
--    Rsyntax INTEGER {
--        unknown(1),
--        other(2),
--        internalError(3),
--        localDisconnected(4),
--        remoteDisconnected(5),
--        networkCongestion(6),
--        mediaNegotiationFailure(7),
--        securityConfigMismatched(8),
--        incompatibleRemoteEndPt(9),
--        serviceUnavailable(10),
--        remoteTerminatedWithError(11)
--        }
    ACCESS read-only
    STATUS mandatory
    DESCRIPTION
        "This object specifies the call termination reason."
    ::= { ctpcEntry 17 }

ctpcStatStreamTypeTable OBJECT-TYPE
    SYNTAX SEQUENCE OF CtpcStatStreamTypeEntry
    ACCESS not-accessible
    STATUS mandatory
    DESCRIPTION
        "A table of stream type information of a call."
    ::= { ctpcStatObjects 9 }

ctpcStatStreamTypeEntry OBJECT-TYPE
    SYNTAX CtpcStatStreamTypeEntry
    ACCESS not-accessible
    STATUS mandatory
    DESCRIPTION
        "An entry contains information on a particular stream type of
        a call.
        
        The entry will be deleted when the corresponding ctpcEntry
        specified by ctpcIndex is removed."
    INDEX { ctpcIndex, ctpcStreamType }
    ::= { ctpcStatStreamTypeTable 1 }

CtpcStatStreamTypeEntry ::= SEQUENCE {
    ctpcStreamType CtpcStreamMediaType,
    ctpcAvgPeriodLatency Gauge,
    ctpcAvgCallLatency Gauge,
    ctpcMaxPeriodLatency Gauge,
    ctpcMaxCallLatency Gauge,
    ctpcMaxCallLatencyRecTime Gauge,
    ctpcMediaSrcPort Gauge,
    ctpcMediaDestPort Gauge,
    ctpcRxDscpCurrent Dscp,
    ctpcRxDscpPrevious Dscp,
    ctpcRxCoSCurrent QosLayer2Cos,
    ctpcRxCoSPrevious QosLayer2Cos
    }

ctpcStreamType OBJECT-TYPE
    SYNTAX CtpcStreamMediaType
--    Rsyntax INTEGER {
--        video(1),
--        audio(2),
--        content(3)
--        }
    ACCESS not-accessible
    STATUS mandatory
    DESCRIPTION
        "This object specifies the call stream type."
    ::= { ctpcStatStreamTypeEntry 1 }

ctpcAvgPeriodLatency OBJECT-TYPE
    SYNTAX Gauge
--  Units
--    milliseconds
    ACCESS read-only
    STATUS mandatory
    DESCRIPTION
        "This object specifies the average latency for the last
        sample period specified in ctpcSamplePeriod.
        
        When a call is terminated, the value will be reset to '0'."
    ::= { ctpcStatStreamTypeEntry 2 }

ctpcAvgCallLatency OBJECT-TYPE
    SYNTAX Gauge
--  Units
--    milliseconds
    ACCESS read-only
    STATUS mandatory
    DESCRIPTION
        "This object specifies the average latency for the duration
        of a call."
    ::= { ctpcStatStreamTypeEntry 3 }

ctpcMaxPeriodLatency OBJECT-TYPE
    SYNTAX Gauge
--  Units
--    milliseconds
    ACCESS read-only
    STATUS mandatory
    DESCRIPTION
        "This object specifies the maximum latency among all the
        sample periods."
    ::= { ctpcStatStreamTypeEntry 4 }

ctpcMaxCallLatency OBJECT-TYPE
    SYNTAX Gauge
--  Units
--    milliseconds
    ACCESS read-only
    STATUS mandatory
    DESCRIPTION
        "This object specifies the maximum latency for the duration
        of a call."
    ::= { ctpcStatStreamTypeEntry 5 }

ctpcMaxCallLatencyRecTime OBJECT-TYPE
    SYNTAX Gauge
--  Units
--    seconds
    ACCESS read-only
    STATUS mandatory
    DESCRIPTION
        "This object specifies the elapsed time since the call is
        established when the maximum latency of a call is recorded."
    ::= { ctpcStatStreamTypeEntry 6 }

ctpcMediaSrcPort OBJECT-TYPE
    SYNTAX Gauge
    ACCESS read-only
    STATUS mandatory
    DESCRIPTION
        "This object specifies the source port to transmit and receive
        the media."
    ::= { ctpcStatStreamTypeEntry 7 }

ctpcMediaDestPort OBJECT-TYPE
    SYNTAX Gauge
    ACCESS read-only
    STATUS mandatory
    DESCRIPTION
        "This object specifies the dest port to transmit and receive
        the media."
    ::= { ctpcStatStreamTypeEntry 8 }

ctpcRxDscpCurrent OBJECT-TYPE
    SYNTAX Dscp
--    Rsyntax INTEGER(0..63)
    ACCESS read-only
    STATUS mandatory
    DESCRIPTION
        "This object specifies the DSCP marking for the current call's
        incoming stream."
    ::= { ctpcStatStreamTypeEntry 9 }

ctpcRxDscpPrevious OBJECT-TYPE
    SYNTAX Dscp
--    Rsyntax INTEGER(0..63)
    ACCESS read-only
    STATUS mandatory
    DESCRIPTION
        "This object specifies the previous DSCP marking for the
        current call's incoming stream."
    ::= { ctpcStatStreamTypeEntry 10 }

ctpcRxCoSCurrent OBJECT-TYPE
    SYNTAX QosLayer2Cos
--    Rsyntax INTEGER(0..7)
    ACCESS read-only
    STATUS mandatory
    DESCRIPTION
        "This object specifies the COS marking for the current call's
        incoming stream."
    ::= { ctpcStatStreamTypeEntry 11 }

ctpcRxCoSPrevious OBJECT-TYPE
    SYNTAX QosLayer2Cos
--    Rsyntax INTEGER(0..7)
    ACCESS read-only
    STATUS mandatory
    DESCRIPTION
        "This object specifies the previous COS marking for the
        current call's incoming stream."
    ::= { ctpcStatStreamTypeEntry 12 }

ctpcStatStreamSourceTable OBJECT-TYPE
    SYNTAX SEQUENCE OF CtpcStatStreamSourceEntry
    ACCESS not-accessible
    STATUS mandatory
    DESCRIPTION
        "A table for call stream source information."
    ::= { ctpcStatObjects 10 }

ctpcStatStreamSourceEntry OBJECT-TYPE
    SYNTAX CtpcStatStreamSourceEntry
    ACCESS not-accessible
    STATUS mandatory
    DESCRIPTION
        "An entry contains a stream source information of a call.
        
        The entry will be deleted when the corresponding ctpcEntry
        specified by ctpcIndex is removed."
    INDEX { ctpcIndex, ctpcStreamType, ctpcStreamSource }
    ::= { ctpcStatStreamSourceTable 1 }

CtpcStatStreamSourceEntry ::= SEQUENCE {
    ctpcStreamSource CtpcStreamSourceType,
    ctpcTxActive TruthValue,
    ctpcTxTotalBytes Counter,
    ctpcTxTotalPackets Counter,
    ctpcTxLostPackets Counter,
    ctpcTxPeriodLostPackets Gauge,
    ctpcTxCallLostPackets Gauge,
    ctpcTxIDRPackets Counter,
    ctpcTxShapingWindow Gauge,
    ctpcRxActive TruthValue,
    ctpcRxTotalBytes Counter,
    ctpcRxTotalPackets Counter,
    ctpcRxLostPackets Counter,
    ctpcRxPeriodLostPackets Gauge,
    ctpcRxCallLostPackets Gauge,
    ctpcRxOutOfOrderPackets Counter,
    ctpcRxDuplicatePackets Counter,
    ctpcRxLatePackets Counter,
    ctpcRxIDRPackets Counter,
    ctpcRxShapingWindow Gauge,
    ctpcRxCallAuthFailure Counter,
    ctpcAvgPeriodJitter Unsigned64,
    ctpcAvgCallJitter Unsigned64,
    ctpcMaxPeriodJitter Unsigned64,
    ctpcMaxCallJitter Unsigned64,
    ctpcMaxCallJitterRecTime Gauge,
    ctpcTxCodec CtpcCodecType,
    ctpcTxFrameRate Gauge,
    ctpcRxCodec CtpcCodecType,
    ctpcRxFrameRate Gauge,
    ctpcTxVideoHorzPixels Gauge,
    ctpcTxVideoVertPixels Gauge,
    ctpcRxVideoHorzPixels Gauge,
    ctpcRxVideoVertPixels Gauge,
    ctpcTxCallBitRate Gauge,
    ctpcTxPeriodBitRate Gauge,
    ctpcRxCallBitRate Gauge,
    ctpcRxPeriodBitRate Gauge,
    ctpcRxMaxPeriodLostPackets Gauge,
    ctpcRxMaxCallLostPackets Gauge,
    ctpcRxMaxCallLostPacketsRecTime Gauge
    }

ctpcStreamSource OBJECT-TYPE
    SYNTAX CtpcStreamSourceType
--    Rsyntax INTEGER {
--        secCodec1(1),
--        priCodec(2),
--        secCodec2(3),
--        auxiliary1(4),
--        secLegacy1(5),
--        priLegacy(6),
--        secLegacy2(7),
--        auxiliary2(8)
--        }
    ACCESS not-accessible
    STATUS mandatory
    DESCRIPTION
        "This object specifies the call stream source."
    ::= { ctpcStatStreamSourceEntry 1 }

ctpcTxActive OBJECT-TYPE
    SYNTAX TruthValue
--    Rsyntax INTEGER {
--        true(1),
--        false(2)
--        }
    ACCESS read-only
    STATUS mandatory
    DESCRIPTION
        "This object is set to 'true' if data transmit from a
        stream source is 'active'."
    ::= { ctpcStatStreamSourceEntry 2 }

ctpcTxTotalBytes OBJECT-TYPE
    SYNTAX --?? syntax is not convertable to SMIv1
           Counter
--  Units
--    bytes
    ACCESS read-only
    STATUS mandatory
    DESCRIPTION
        "This object specifies the total number of bytes transmitted
        from a stream source."
    ::= { ctpcStatStreamSourceEntry 3 }

ctpcTxTotalPackets OBJECT-TYPE
    SYNTAX --?? syntax is not convertable to SMIv1
           Counter
--  Units
--    packets
    ACCESS read-only
    STATUS mandatory
    DESCRIPTION
        "This object specifies the total number of packets transmitted
        from a stream source."
    ::= { ctpcStatStreamSourceEntry 4 }

ctpcTxLostPackets OBJECT-TYPE
    SYNTAX --?? syntax is not convertable to SMIv1
           Counter
--  Units
--    packets
    ACCESS read-only
    STATUS mandatory
    DESCRIPTION
        "This object specifies the number packets failed to deliver
        from a stream source."
    ::= { ctpcStatStreamSourceEntry 5 }

ctpcTxPeriodLostPackets OBJECT-TYPE
    SYNTAX Gauge(0..100000000)
--  Units
--    micropercent
    ACCESS read-only
    STATUS mandatory
    DESCRIPTION
        "This object specifies the micropercent of packets failed
        to deliver from a stream source within the last sample 
        period specified in ctpcSamplePeriod.
        
        When a call is terminated, the value will be reset to '0'."
    ::= { ctpcStatStreamSourceEntry 6 }

ctpcTxCallLostPackets OBJECT-TYPE
    SYNTAX Gauge(0..100000000)
--  Units
--    micropercent
    ACCESS read-only
    STATUS mandatory
    DESCRIPTION
        "This object specifies the micropercent of packets failed
        to deliver from a stream source for the duration of
        a call."
    ::= { ctpcStatStreamSourceEntry 7 }

ctpcTxIDRPackets OBJECT-TYPE
    SYNTAX --?? syntax is not convertable to SMIv1
           Counter
--  Units
--    packets
    ACCESS read-only
    STATUS mandatory
    DESCRIPTION
        "This object specifies the number of IDR packets transmitted
        from a stream source."
    ::= { ctpcStatStreamSourceEntry 8 }

ctpcTxShapingWindow OBJECT-TYPE
    SYNTAX Gauge
--  Units
--    milliseconds
    ACCESS read-only
    STATUS mandatory
    DESCRIPTION
        "This object specifies the time span between the last
        video packet and first video packet of a transmitted video 
        frame.
        
        This object is only applicable for video stream type."
    ::= { ctpcStatStreamSourceEntry 9 }

ctpcRxActive OBJECT-TYPE
    SYNTAX TruthValue
--    Rsyntax INTEGER {
--        true(1),
--        false(2)
--        }
    ACCESS read-only
    STATUS mandatory
    DESCRIPTION
        "This object is set to 'true' if data received by
        a stream source is 'active'."
    ::= { ctpcStatStreamSourceEntry 10 }

ctpcRxTotalBytes OBJECT-TYPE
    SYNTAX --?? syntax is not convertable to SMIv1
           Counter
--  Units
--    bytes
    ACCESS read-only
    STATUS mandatory
    DESCRIPTION
        "This object specifies the total number of bytes received by
        a stream source."
    ::= { ctpcStatStreamSourceEntry 11 }

ctpcRxTotalPackets OBJECT-TYPE
    SYNTAX --?? syntax is not convertable to SMIv1
           Counter
--  Units
--    packets
    ACCESS read-only
    STATUS mandatory
    DESCRIPTION
        "This object specifies the total number of packets received by
        a stream source."
    ::= { ctpcStatStreamSourceEntry 12 }

ctpcRxLostPackets OBJECT-TYPE
    SYNTAX --?? syntax is not convertable to SMIv1
           Counter
--  Units
--    packets
    ACCESS read-only
    STATUS mandatory
    DESCRIPTION
        "This object specifies the number packets failed to reach
        a stream source."
    ::= { ctpcStatStreamSourceEntry 13 }

ctpcRxPeriodLostPackets OBJECT-TYPE
    SYNTAX Gauge(0..100000000)
--  Units
--    micropercent
    ACCESS read-only
    STATUS mandatory
    DESCRIPTION
        "This object specifies the micropercent of packets failed
        to reach a stream source within the last sample period 
        specified in ctpcSamplePeriod.
        
        When a call is terminated, the value will be reset to '0'."
    ::= { ctpcStatStreamSourceEntry 14 }

ctpcRxCallLostPackets OBJECT-TYPE
    SYNTAX Gauge(0..100000000)
--  Units
--    micropercent
    ACCESS read-only
    STATUS mandatory
    DESCRIPTION
        "This object specifies the micropercent of packets failed
        to reach a stream source."
    ::= { ctpcStatStreamSourceEntry 15 }

ctpcRxOutOfOrderPackets OBJECT-TYPE
    SYNTAX --?? syntax is not convertable to SMIv1
           Counter
--  Units
--    packets
    ACCESS read-only
    STATUS mandatory
    DESCRIPTION
        "This object specifies the number packets received out of
        order by a stream source."
    ::= { ctpcStatStreamSourceEntry 16 }

ctpcRxDuplicatePackets OBJECT-TYPE
    SYNTAX --?? syntax is not convertable to SMIv1
           Counter
--  Units
--    packets
    ACCESS read-only
    STATUS mandatory
    DESCRIPTION
        "This object specifies the number duplicated packets
        received by a stream source."
    ::= { ctpcStatStreamSourceEntry 17 }

ctpcRxLatePackets OBJECT-TYPE
    SYNTAX --?? syntax is not convertable to SMIv1
           Counter
--  Units
--    packets
    ACCESS read-only
    STATUS mandatory
    DESCRIPTION
        "This object specifies the number late packets
        received by a stream source."
    ::= { ctpcStatStreamSourceEntry 18 }

ctpcRxIDRPackets OBJECT-TYPE
    SYNTAX --?? syntax is not convertable to SMIv1
           Counter
--  Units
--    packets
    ACCESS read-only
    STATUS mandatory
    DESCRIPTION
        "This object specifies the number of IDR packets received
        by a stream source."
    ::= { ctpcStatStreamSourceEntry 19 }

ctpcRxShapingWindow OBJECT-TYPE
    SYNTAX Gauge
--  Units
--    milliseconds
    ACCESS read-only
    STATUS mandatory
    DESCRIPTION
        "This object specifies the time span between the last
        video packet and first video packet of a received video frame.
        
        This object is only applicable for video stream type."
    ::= { ctpcStatStreamSourceEntry 20 }

ctpcRxCallAuthFailure OBJECT-TYPE
    SYNTAX --?? syntax is not convertable to SMIv1
           Counter
--  Units
--    packets
    ACCESS read-only
    STATUS mandatory
    DESCRIPTION
        "This object specifies the number of authenticated packets
        for which verification failed."
    ::= { ctpcStatStreamSourceEntry 21 }

ctpcAvgPeriodJitter OBJECT-TYPE
    SYNTAX --?? syntax is not convertable to SMIv1
           Unsigned64
--    Rsyntax Counter
--  Units
--    milliseconds
    ACCESS read-only
    STATUS mandatory
    DESCRIPTION
        "This object specifies the average jitter of a stream source
        for a Telepresence call from the most recent sample period 
        specified in ctpcSamplePeriod.
        
        When a call is terminated, the value will be reset to '0'."
    ::= { ctpcStatStreamSourceEntry 22 }

ctpcAvgCallJitter OBJECT-TYPE
    SYNTAX --?? syntax is not convertable to SMIv1
           Unsigned64
--    Rsyntax Counter
--  Units
--    milliseconds
    ACCESS read-only
    STATUS mandatory
    DESCRIPTION
        "This object specifies the average jitter of a
        stream source for a Telepresence call among all the sample
        periods specified in ctpcSamplePeriod."
    ::= { ctpcStatStreamSourceEntry 23 }

ctpcMaxPeriodJitter OBJECT-TYPE
    SYNTAX --?? syntax is not convertable to SMIv1
           Unsigned64
--    Rsyntax Counter
--  Units
--    milliseconds
    ACCESS read-only
    STATUS mandatory
    DESCRIPTION
        "This object specifies the maximum jitter of a
        stream source for a Telepresence call
        for any sample period specified in ctpcSamplePeriod. 
        
        When a call is terminated, the value will be reset to '0'."
    ::= { ctpcStatStreamSourceEntry 24 }

ctpcMaxCallJitter OBJECT-TYPE
    SYNTAX --?? syntax is not convertable to SMIv1
           Unsigned64
--    Rsyntax Counter
--  Units
--    milliseconds
    ACCESS read-only
    STATUS mandatory
    DESCRIPTION
        "This object specifies the maximum average jitter of a
        stream source for a Telepresence call among all the sample
        periods specified in ctpcSamplePeriod."
    ::= { ctpcStatStreamSourceEntry 25 }

ctpcMaxCallJitterRecTime OBJECT-TYPE
    SYNTAX Gauge
--  Units
--    seconds
    ACCESS read-only
    STATUS mandatory
    DESCRIPTION
        "This object specifies the elapsed time since the call is
        established when the maximum jitter of a stream source is 
        recorded."
    ::= { ctpcStatStreamSourceEntry 26 }

ctpcTxCodec OBJECT-TYPE
    SYNTAX CtpcCodecType
--    Rsyntax INTEGER {
--        unknown(1),
--        other(2),
--        aaclc(3),
--        aacld(4),
--        g711A(5),
--        g711U(6),
--        g722(7),
--        g7221(8),
--        g728(9),
--        g729(10),
--        h263(11),
--        h264(12),
--        aacldLatm(13)
--        }
    ACCESS read-only
    STATUS mandatory
    DESCRIPTION
        "This object specifies the transmitted media codec type of a
        stream source."
    ::= { ctpcStatStreamSourceEntry 27 }

ctpcTxFrameRate OBJECT-TYPE
    SYNTAX Gauge
--  Units
--    millifps
    ACCESS read-only
    STATUS mandatory
    DESCRIPTION
        "This object specifies the transmitted frame rate of a stream
        source."
    ::= { ctpcStatStreamSourceEntry 28 }

ctpcRxCodec OBJECT-TYPE
    SYNTAX CtpcCodecType
--    Rsyntax INTEGER {
--        unknown(1),
--        other(2),
--        aaclc(3),
--        aacld(4),
--        g711A(5),
--        g711U(6),
--        g722(7),
--        g7221(8),
--        g728(9),
--        g729(10),
--        h263(11),
--        h264(12),
--        aacldLatm(13)
--        }
    ACCESS read-only
    STATUS mandatory
    DESCRIPTION
        "This object specifies the received media codec type of a
        stream source."
    ::= { ctpcStatStreamSourceEntry 29 }

ctpcRxFrameRate OBJECT-TYPE
    SYNTAX Gauge
--  Units
--    millifps
    ACCESS read-only
    STATUS mandatory
    DESCRIPTION
        "This object specifies the received frame rate of a stream
        source."
    ::= { ctpcStatStreamSourceEntry 30 }

ctpcTxVideoHorzPixels OBJECT-TYPE
    SYNTAX Gauge(0..65535)
--  Units
--    pixels
    ACCESS read-only
    STATUS mandatory
    DESCRIPTION
        "This object specifies the number of horizontal pixels
        in the outgoing video stream.
        
        When a call is terminated, the value will be the last 
        recorded number of horizontal pixels for the outgoing
        video stream."
    ::= { ctpcStatStreamSourceEntry 31 }

ctpcTxVideoVertPixels OBJECT-TYPE
    SYNTAX Gauge(0..65535)
--  Units
--    pixels
    ACCESS read-only
    STATUS mandatory
    DESCRIPTION
        "This object specifies the number of vertical pixels
        in the outgoing video stream. 
        
        When a call is terminated, the value will be the last 
        recorded number of vertical pixels for the outgoing
        video stream."
    ::= { ctpcStatStreamSourceEntry 32 }

ctpcRxVideoHorzPixels OBJECT-TYPE
    SYNTAX Gauge(0..65535)
--  Units
--    pixels
    ACCESS read-only
    STATUS mandatory
    DESCRIPTION
        "This object specifies the number of horizontal pixels
        in the incoming video stream.
        
        When a call is terminated, the value will be the last 
        recorded number of horizontal pixels for the incoming
        video stream."
    ::= { ctpcStatStreamSourceEntry 33 }

ctpcRxVideoVertPixels OBJECT-TYPE
    SYNTAX Gauge(0..65535)
--  Units
--    pixels
    ACCESS read-only
    STATUS mandatory
    DESCRIPTION
        "This object specifies the number of vertical pixels
        in the incoming video streams.
        
        When a call is terminated, the value will be the last 
        recorded number of vertical pixels for the incoming video
        stream."
    ::= { ctpcStatStreamSourceEntry 34 }

ctpcTxCallBitRate OBJECT-TYPE
    SYNTAX Gauge
--  Units
--    Kbps
    ACCESS read-only
    STATUS mandatory
    DESCRIPTION
        "This object indicates the bit rate transmitted from a
        stream source."
    ::= { ctpcStatStreamSourceEntry 35 }

ctpcTxPeriodBitRate OBJECT-TYPE
    SYNTAX Gauge
--  Units
--    Kbps
    ACCESS read-only
    STATUS mandatory
    DESCRIPTION
        "This object indicates the bit rate transmitted from a
        stream source within the last sample period that
        specified in ctpcSamplePeriod."
    ::= { ctpcStatStreamSourceEntry 36 }

ctpcRxCallBitRate OBJECT-TYPE
    SYNTAX Gauge
--  Units
--    Kbps
    ACCESS read-only
    STATUS mandatory
    DESCRIPTION
        "This object indicates the bit rate received from a
        stream source."
    ::= { ctpcStatStreamSourceEntry 37 }

ctpcRxPeriodBitRate OBJECT-TYPE
    SYNTAX Gauge
--  Units
--    Kbps
    ACCESS read-only
    STATUS mandatory
    DESCRIPTION
        "This object indicates the bit rate received from a
        stream source within the last sample period that
        specified in ctpcSamplePeriod."
    ::= { ctpcStatStreamSourceEntry 38 }

ctpcRxMaxPeriodLostPackets OBJECT-TYPE
    SYNTAX Gauge(0..100000000)
--  Units
--    micropercent
    ACCESS read-only
    STATUS mandatory
    DESCRIPTION
        "This object indicates the maximum micropercent of packets
        failed to reach a stream source within the last sample
        period that specified in ctpcSamplePeriod.
        
        When a call is terminated, the value will be reset to '0'."
    ::= { ctpcStatStreamSourceEntry 39 }

ctpcRxMaxCallLostPackets OBJECT-TYPE
    SYNTAX Gauge(0..100000000)
--  Units
--    micropercent
    ACCESS read-only
    STATUS mandatory
    DESCRIPTION
        "This object indicates the maximum micropercent of packets failed
        to reach a stream source for the duration of a call."
    ::= { ctpcStatStreamSourceEntry 40 }

ctpcRxMaxCallLostPacketsRecTime OBJECT-TYPE
    SYNTAX Gauge
--  Units
--    seconds
    ACCESS read-only
    STATUS mandatory
    DESCRIPTION
        "This object indicates the elapsed time since the call is
        established when the maximum packet loss of a call is recorded."
    ::= { ctpcStatStreamSourceEntry 41 }

ctpcStatEventHistTableSize OBJECT-TYPE
    SYNTAX Gauge(0..500)
    ACCESS read-write
    STATUS mandatory
    DESCRIPTION
        "This object specifies the number of entries that the
        ctpcStatEventHistoryTable can contain.  When the 
        capacity of the ctpcStatEventHistoryTable has reached,
        the value specified by this object, then the agent 
        deletes the oldest entry in order to accommodate
        the new entry. A value of '0' prevents any history
        from being retained."
    DEFVAL { 10 }
    ::= { ctpcStatEventHistory 1 }

ctpcStatEventHistLastIndex OBJECT-TYPE
    SYNTAX Gauge(0..4294967295)
    ACCESS read-only
    STATUS mandatory
    DESCRIPTION
        "This object specifies the value of the
        ctpcStatEventHistIndex object corresponding to the
        last entry added to the table by the agent.
        
        If the management client uses the notifications defined by
        this module, then it can poll this object to determine
        whether it has missed a notification sent by the agent."
    ::= { ctpcStatEventHistory 2 }

ctpcStatEventHistoryTable OBJECT-TYPE
    SYNTAX SEQUENCE OF CtpcStatEventHistoryEntry
    ACCESS not-accessible
    STATUS mandatory
    DESCRIPTION
        "This table contains a history of Telepresence
        call monitoring thresholds crossed events.
        
        After management system initialization  (i.e. when 
        sysUpTime is reset to zero), this table
        records all notifications until it reaches its
        capacity specified in ctpcStatEventHistTableSize.
        Thereafter, it remains full by retaining the most recent 
        notifications."
    ::= { ctpcStatEventHistory 3 }

ctpcStatEventHistoryEntry OBJECT-TYPE
    SYNTAX CtpcStatEventHistoryEntry
    ACCESS not-accessible
    STATUS mandatory
    DESCRIPTION
        "An entry contains information about a Telepresence
        call monitoring threshold crossed event."
    INDEX { ctpcStatEventHistoryIndex }
    ::= { ctpcStatEventHistoryTable 1 }

CtpcStatEventHistoryEntry ::= SEQUENCE {
    ctpcStatEventHistoryIndex Gauge,
    ctpcStatEventMonObjectInst VariablePointer,
    ctpcStatEventCrossedValue Unsigned64,
    ctpcStatEventCrossedType CtpcStatThreshCrossedType,
    ctpcStatEventTimeStamp TimeTicks
    }

ctpcStatEventHistoryIndex OBJECT-TYPE
    SYNTAX Gauge(1..4294967295)
    ACCESS not-accessible
    STATUS mandatory
    DESCRIPTION
        "A unique non-zero integer value that identifies a
        row in this table.
        
        The value of this table starts from '1' and monotonically
        increases for each threshold crossed event
        received by the agent. If the value of this object is 
        '4294967295', the agent will reset it to '1' upon receiving the 
        next event."
    ::= { ctpcStatEventHistoryEntry 1 }

ctpcStatEventMonObjectInst OBJECT-TYPE
    SYNTAX VariablePointer
--    Rsyntax OBJECT IDENTIFIER
    ACCESS read-only
    STATUS mandatory
    DESCRIPTION
        "This object specifies a complete OID of a
        monitoring object which was crossed.
        
        For example, the OID of ctpcAvgPeriodLatency.1.video
        would represent video latency of a call with 
        call index '1' crossed the threshold set by the corresponding
        ctpcStatMonitoredEntry."
    ::= { ctpcStatEventHistoryEntry 2 }

ctpcStatEventCrossedValue OBJECT-TYPE
    SYNTAX --?? syntax is not convertable to SMIv1
           Unsigned64
--    Rsyntax Counter
    ACCESS read-only
    STATUS mandatory
    DESCRIPTION
        "This object specifies the value of monitoring object
        when the threshold was crossed."
    ::= { ctpcStatEventHistoryEntry 3 }

ctpcStatEventCrossedType OBJECT-TYPE
    SYNTAX CtpcStatThreshCrossedType
--    Rsyntax INTEGER {
--        risingThreshold(1),
--        fallingThreshold(2)
--        }
    ACCESS read-only
    STATUS mandatory
    DESCRIPTION
        "This object specifies the type of threshold which
        was crossed and thereby triggered this event."
    ::= { ctpcStatEventHistoryEntry 4 }

ctpcStatEventTimeStamp OBJECT-TYPE
    SYNTAX TimeTicks
    ACCESS read-only
    STATUS mandatory
    DESCRIPTION
        "This object specifies the value of the sysUpTime object at the
        time the notification was generated."
    ::= { ctpcStatEventHistoryEntry 5 }

ctpcMgmtSysConnEventHistTableSize OBJECT-TYPE
    SYNTAX Gauge(0..500)
    ACCESS read-write
    STATUS mandatory
    DESCRIPTION
        "This object specifies the number of entries that the
        ctpcMgmtSysConnEventHistoryTable can contain.  When the 
        capacity of the ctpcMgmtSysConnEventHistoryTable has reached,
        the value specified by this object, then the agent 
        deletes the oldest entry in order to accommodate
        the new entry. A value of '0' prevents any history
        from being retained.
        
        Some agents restrict the maximum value of this object to
        be less than 500."
    DEFVAL { 10 }
    ::= { ctpcMgmtSysConnEventHistory 1 }

ctpcMgmtSysConnEventHistLastIndex OBJECT-TYPE
    SYNTAX Gauge(0..4294967295)
    ACCESS read-only
    STATUS mandatory
    DESCRIPTION
        "This object specifies the value of the
        ctpcMgmtSysConnEventHistIndex object corresponding to the
        last entry added to the table by the agent.
        
        If the management client uses the notifications defined by
        this module, then it can poll this object to determine
        whether it has missed a notification sent by the agent."
    ::= { ctpcMgmtSysConnEventHistory 2 }

ctpcMgmtSysConnEventHistoryTable OBJECT-TYPE
    SYNTAX SEQUENCE OF CtpcMgmtSysConnEventHistoryEntry
    ACCESS not-accessible
    STATUS mandatory
    DESCRIPTION
        "This table contains a history of call management system
        connection state changes.
        
        After management system initialization  (i.e. when 
        sysUpTime is reset to zero), this table
        records all notifications until it reaches its
        capacity specified in ctpcMgmtSysConnEventHistTableSize.
        Thereafter, it remains full by retaining the most recent 
        notifications."
    ::= { ctpcMgmtSysConnEventHistory 3 }

ctpcMgmtSysConnEventHistoryEntry OBJECT-TYPE
    SYNTAX CtpcMgmtSysConnEventHistoryEntry
    ACCESS not-accessible
    STATUS mandatory
    DESCRIPTION
        "An entry contains information about a call management
        system connection state change event."
    INDEX { ctpcMgmtSysConnEventHistoryIndex }
    ::= { ctpcMgmtSysConnEventHistoryTable 1 }

CtpcMgmtSysConnEventHistoryEntry ::= SEQUENCE {
    ctpcMgmtSysConnEventHistoryIndex Gauge,
    ctpcMgmtSysConnEventStatus CtpcMgmtSysConnStatusCode,
    ctpcMgmtSysConnEventSIPRespCode Gauge,
    ctpcMgmtSysConnEventTimeStamp TimeTicks
    }

ctpcMgmtSysConnEventHistoryIndex OBJECT-TYPE
    SYNTAX Gauge(1..4294967295)
    ACCESS not-accessible
    STATUS mandatory
    DESCRIPTION
        "A unique non-zero integer value that identifies a
        row in this table.
        
        The value of this table starts from '1' and monotonically
        increases for each management system connection event
        received by the agent. If the value of this object is 
        '4294967295', the agent will reset it to '1' upon receiving the 
        next event."
    ::= { ctpcMgmtSysConnEventHistoryEntry 1 }

ctpcMgmtSysConnEventStatus OBJECT-TYPE
    SYNTAX CtpcMgmtSysConnStatusCode
--    Rsyntax INTEGER {
--        unknown(1),
--        other(2),
--        internalError(3),
--        notRegister(4),
--        registered(5),
--        registraionFailure(6)
--        }
    ACCESS read-only
    STATUS mandatory
    DESCRIPTION
        "This object specifies a call management system
        connection state when the event happened."
    ::= { ctpcMgmtSysConnEventHistoryEntry 2 }

ctpcMgmtSysConnEventSIPRespCode OBJECT-TYPE
    SYNTAX Gauge
    ACCESS read-only
    STATUS mandatory
    DESCRIPTION
        "This object specifies SIP response code from
        call management system when the event happened."
    REFERENCE
        "RFC 3261, section 21"
    ::= { ctpcMgmtSysConnEventHistoryEntry 3 }

ctpcMgmtSysConnEventTimeStamp OBJECT-TYPE
    SYNTAX TimeTicks
    ACCESS read-only
    STATUS mandatory
    DESCRIPTION
        "This object specifies the value of the sysUpTime object at the
        time the notification was generated."
    ::= { ctpcMgmtSysConnEventHistoryEntry 4 }

ctpcMgmtSysConnFailNotification TRAP-TYPE
-- Reverse mappable trap
    ENTERPRISE ciscoTelepresenceCallMIB
    VARIABLES {
        ctpcMgmtSysAddrType, ctpcMgmtSysAddr }
--  Status
--    deprecated
    DESCRIPTION
        "This notification is sent when a call management system
        connection failure occurs.
        
        This notification is deprecated in favor of 
        ctpcMgmtSysConnEventNotification."
    ::= 1

ctpcStatNotificaion TRAP-TYPE
-- Reverse mappable trap
    ENTERPRISE ciscoTelepresenceCallMIB
    VARIABLES {
        ctpcStatEventMonObjectInst, ctpcStatEventCrossedValue, 
        ctpcStatEventCrossedType }
--  Status
--    mandatory
    DESCRIPTION
        "This notification is sent when a call monitoring threshold is
        crossed."
    ::= 2

ctpcMgmtSysConnEventNotification TRAP-TYPE
-- Reverse mappable trap
    ENTERPRISE ciscoTelepresenceCallMIB
    VARIABLES {
        ctpcMgmtSysAddrType, ctpcMgmtSysAddr, ctpcMgmtSysConnStatus, 
        ctpcMgmtSysSIPRespCode }
--  Status
--    mandatory
    DESCRIPTION
        "This notification is sent when a call management system
        connection state change occurs."
    ::= 3

ciscoTpCallConfigurationGroup OBJECT IDENTIFIER ::= { ciscoTpCallMIBGroups 1 }
-- OBJECT-GROUP
--  Status
--    mandatory
--  Descr
--    A collection of objects providing the call event monitoring and
--    notification configuration.
--  objects
--    ctpcStatNotifyEnable, ctpcMgmtSysConnNotifyEnable, 
--    ctpcStatMonitoredUnit, ctpcStatRisingThreshold, 
--    ctpcStatFallingThreshold, ctpcStatStartupAlarm, 
--    ctpcStatMonitoredStatus

ciscoTpCallInformationGroup OBJECT IDENTIFIER ::= { ciscoTpCallMIBGroups 2 }
-- OBJECT-GROUP
--  Status
--    mandatory
--  Descr
--    A collection of objects providing call management system
--    information as well as system caller ID information.
--  objects
--    ctpcLocalDirNum, ctpcLocalAddrType, ctpcLocalAddr, 
--    ctpcActiveMgmtSysIndex, ctpcMode, ctpcMgmtSysAddrType, 
--    ctpcMgmtSysAddr

ciscoTpCallStatisticsGroup OBJECT IDENTIFIER ::= { ciscoTpCallMIBGroups 3 }
-- OBJECT-GROUP
--  Status
--    mandatory
--  Descr
--    A collection of objects providing Telepresence
--    call's statistical information.
--  objects
--    ctpcStatOverallCalls, ctpcStatOverallCallTime, 
--    ctpcStatTotalCalls, ctpcStatTotalCallTime, ctpcSamplePeriod, 
--    ctpcTableSize, ctpcTableLastIndex, ctpcRemoteDirNum, 
--    ctpcLocalSIPCallId, ctpcTxDestAddrType, ctpcTxDestAddr, 
--    ctpcStartDateAndTime, ctpcDuration, ctpcType, ctpcSecurity, 
--    ctpcDirection, ctpcState, ctpcInitialBitRate, 
--    ctpcLatestBitRate, ctpcRowStatus, ctpcAvgPeriodLatency, 
--    ctpcAvgCallLatency, ctpcMaxPeriodLatency, ctpcMaxCallLatency, 
--    ctpcMaxCallLatencyRecTime, ctpcTxActive, ctpcTxTotalBytes, 
--    ctpcTxTotalPackets, ctpcTxLostPackets, 
--    ctpcTxPeriodLostPackets, ctpcTxCallLostPackets, 
--    ctpcTxIDRPackets, ctpcTxShapingWindow, ctpcRxActive, 
--    ctpcRxTotalBytes, ctpcRxTotalPackets, ctpcRxLostPackets, 
--    ctpcRxPeriodLostPackets, ctpcRxCallLostPackets, 
--    ctpcRxOutOfOrderPackets, ctpcRxDuplicatePackets, 
--    ctpcRxLatePackets, ctpcRxIDRPackets, ctpcRxShapingWindow, 
--    ctpcRxCallAuthFailure, ctpcAvgPeriodJitter, ctpcAvgCallJitter, 
--    ctpcMaxPeriodJitter, ctpcMaxCallJitter, 
--    ctpcMaxCallJitterRecTime

ciscoTpCallEventHistoryGroup OBJECT IDENTIFIER ::= { ciscoTpCallMIBGroups 4 }
-- OBJECT-GROUP
--  Status
--    mandatory
--  Descr
--    A collection of objects providing Telepresence
--    call monitoring crossed event information.
--  objects
--    ctpcStatEventHistTableSize, ctpcStatEventHistLastIndex, 
--    ctpcStatEventMonObjectInst, ctpcStatEventCrossedValue, 
--    ctpcStatEventCrossedType, ctpcStatEventTimeStamp

ciscoTpCallMgmtSysConnEventHistGroup OBJECT IDENTIFIER ::= { ciscoTpCallMIBGroups 6 }
-- OBJECT-GROUP
--  Status
--    mandatory
--  Descr
--    A collection of objects providing call management
--    system connection changes event information.
--  objects
--    ctpcMgmtSysConnEventHistTableSize, 
--    ctpcMgmtSysConnEventHistLastIndex, ctpcMgmtSysConnEventStatus, 
--    ctpcMgmtSysConnEventSIPRespCode, 
--    ctpcMgmtSysConnEventTimeStamp

ciscoTpCallInformationGroupSup1 OBJECT IDENTIFIER ::= { ciscoTpCallMIBGroups 7 }
-- OBJECT-GROUP
--  Status
--    mandatory
--  Descr
--    A supplemental group of ciscoTpCallInformationGroup.
--  objects
--    ctpcMgmtSysConnStatus, ctpcMgmtSysSIPRespCode

ciscoTpCallStatisticsGroupSup1 OBJECT IDENTIFIER ::= { ciscoTpCallMIBGroups 8 }
-- OBJECT-GROUP
--  Status
--    mandatory
--  Descr
--    A supplemental group of ciscoTpCallStatisticsGroup.
--  objects
--    ctpcAttributes, ctpcRemoteDevice, ctpcTxCodec, 
--    ctpcTxFrameRate, ctpcRxCodec, ctpcRxFrameRate

ciscoTpCallStatisticsGroupSup2 OBJECT IDENTIFIER ::= { ciscoTpCallMIBGroups 10 }
-- OBJECT-GROUP
--  Status
--    mandatory
--  Descr
--    A supplemental group of ciscoTpCallStatisticsGroup.
--  objects
--    ctpcCallTermReason, ctpcMediaSrcPort, ctpcMediaDestPort, 
--    ctpcRxVideoHorzPixels, ctpcRxVideoVertPixels, 
--    ctpcTxVideoHorzPixels, ctpcTxVideoVertPixels

ciscoTpCallStatisticsGroupSup3 OBJECT IDENTIFIER ::= { ciscoTpCallMIBGroups 11 }
-- OBJECT-GROUP
--  Status
--    mandatory
--  Descr
--    A supplemental group of ciscoTpCallStatisticsGroup.
--  objects
--    ctpcTxCallBitRate, ctpcTxPeriodBitRate, ctpcRxCallBitRate, 
--    ctpcRxPeriodBitRate, ctpcRxMaxPeriodLostPackets, 
--    ctpcRxMaxCallLostPackets, ctpcRxMaxCallLostPacketsRecTime, 
--    ctpcTxDscpTelepresenceConfigured, ctpcTxDscpAudioConfigured, 
--    ctpcRxDscpCurrent, ctpcRxDscpPrevious, ctpcRxCoSCurrent, 
--    ctpcRxCoSPrevious

ciscoTpCallInformationGroupSup2 OBJECT IDENTIFIER ::= { ciscoTpCallMIBGroups 12 }
-- OBJECT-GROUP
--  Status
--    mandatory
--  Descr
--    A supplemental group of ciscoTpCallInformationGroup.
--  objects
--    ctpcExtNumberMask

ciscoTpCallNotificationGroup OBJECT IDENTIFIER ::= { ciscoTpCallMIBGroups 5 }
-- NOTIFICATION-GROUP
--  Status
--    deprecated
--  Descr
--    A collection of event notifications.
--  notifications
--    ctpcMgmtSysConnFailNotification, ctpcStatNotificaion

ciscoTpCallNotificationGroupRev1 OBJECT IDENTIFIER ::= { ciscoTpCallMIBGroups 9 }
-- NOTIFICATION-GROUP
--  Status
--    mandatory
--  Descr
--    A collection of event notifications.
--  notifications
--    ctpcMgmtSysConnEventNotification, ctpcStatNotificaion

ciscoTpCallMIBCompliance OBJECT IDENTIFIER ::= { ciscoTpCallMIBCompliances 1 }
-- MODULE-COMPLIANCE
--  Status
--    deprecated
--  Descr
--    The compliance statement for entities which implement the Cisco
--    Telepresence Call MIB.
--  Module
--    >>current<<
--   MandGroup
--    ciscoTpCallInformationGroup
--   MandGroup
--    ciscoTpCallStatisticsGroup
--   OptGroup
--    ciscoTpCallConfigurationGroup
--   OptGroup
--    ciscoTpCallEventHistoryGroup
--   OptGroup
--    ciscoTpCallNotificationGroup
--   ObjVar
--    ctpcStatNotifyEnable
--   ObjVar
--    ctpcMgmtSysConnNotifyEnable
--   ObjVar
--    ctpcSamplePeriod
--   ObjVar
--    ctpcTableSize
--   ObjVar
--    ctpcType
--   ObjVar
--    ctpcSecurity
--   ObjVar
--    ctpcInitialBitRate
--   ObjVar
--    ctpcRowStatus
--   ObjVar
--    ctpcState
--   ObjVar
--    ctpcStatEventHistTableSize

ciscoTpCallMIBComplianceRev1 OBJECT IDENTIFIER ::= { ciscoTpCallMIBCompliances 2 }
-- MODULE-COMPLIANCE
--  Status
--    deprecated
--  Descr
--    The compliance statement for entities which implement the Cisco
--    Telepresence Call MIB.
--  Module
--    >>current<<
--   MandGroup
--    ciscoTpCallInformationGroup
--   MandGroup
--    ciscoTpCallInformationGroupSup1
--   MandGroup
--    ciscoTpCallStatisticsGroup
--   MandGroup
--    ciscoTpCallStatisticsGroupSup1
--   OptGroup
--    ciscoTpCallConfigurationGroup
--   OptGroup
--    ciscoTpCallEventHistoryGroup
--   OptGroup
--    ciscoTpCallMgmtSysConnEventHistGroup
--   OptGroup
--    ciscoTpCallNotificationGroup
--   ObjVar
--    ctpcStatNotifyEnable
--   ObjVar
--    ctpcMgmtSysConnNotifyEnable
--   ObjVar
--    ctpcSamplePeriod
--   ObjVar
--    ctpcTableSize
--   ObjVar
--    ctpcType
--   ObjVar
--    ctpcSecurity
--   ObjVar
--    ctpcInitialBitRate
--   ObjVar
--    ctpcRowStatus
--   ObjVar
--    ctpcState
--   ObjVar
--    ctpcStatEventHistTableSize
--   ObjVar
--    ctpcMgmtSysConnEventHistTableSize

ciscoTpCallMIBComplianceRev2 OBJECT IDENTIFIER ::= { ciscoTpCallMIBCompliances 3 }
-- MODULE-COMPLIANCE
--  Status
--    deprecated
--  Descr
--    The compliance statement for entities which implement the Cisco
--    Telepresence Call MIB.
--  Module
--    >>current<<
--   MandGroup
--    ciscoTpCallInformationGroup
--   MandGroup
--    ciscoTpCallInformationGroupSup1
--   MandGroup
--    ciscoTpCallStatisticsGroup
--   MandGroup
--    ciscoTpCallStatisticsGroupSup1
--   MandGroup
--    ciscoTpCallStatisticsGroupSup2
--   OptGroup
--    ciscoTpCallConfigurationGroup
--   OptGroup
--    ciscoTpCallEventHistoryGroup
--   OptGroup
--    ciscoTpCallMgmtSysConnEventHistGroup
--   OptGroup
--    ciscoTpCallNotificationGroupRev1
--   ObjVar
--    ctpcStatNotifyEnable
--   ObjVar
--    ctpcMgmtSysConnNotifyEnable
--   ObjVar
--    ctpcSamplePeriod
--   ObjVar
--    ctpcTableSize
--   ObjVar
--    ctpcType
--   ObjVar
--    ctpcSecurity
--   ObjVar
--    ctpcInitialBitRate
--   ObjVar
--    ctpcRowStatus
--   ObjVar
--    ctpcState
--   ObjVar
--    ctpcStatEventHistTableSize
--   ObjVar
--    ctpcMgmtSysConnEventHistTableSize

ciscoTpCallMIBComplianceRev3 OBJECT IDENTIFIER ::= { ciscoTpCallMIBCompliances 4 }
-- MODULE-COMPLIANCE
--  Status
--    deprecated
--  Descr
--    The compliance statement for entities which implement the Cisco
--    Telepresence Call MIB.
--  Module
--    >>current<<
--   MandGroup
--    ciscoTpCallInformationGroup
--   MandGroup
--    ciscoTpCallInformationGroupSup1
--   MandGroup
--    ciscoTpCallStatisticsGroup
--   MandGroup
--    ciscoTpCallStatisticsGroupSup1
--   MandGroup
--    ciscoTpCallStatisticsGroupSup2
--   MandGroup
--    ciscoTpCallStatisticsGroupSup3
--   OptGroup
--    ciscoTpCallConfigurationGroup
--   OptGroup
--    ciscoTpCallEventHistoryGroup
--   OptGroup
--    ciscoTpCallMgmtSysConnEventHistGroup
--   ObjVar
--    ctpcStatNotifyEnable
--   ObjVar
--    ctpcMgmtSysConnNotifyEnable
--   ObjVar
--    ctpcSamplePeriod
--   ObjVar
--    ctpcTableSize
--   ObjVar
--    ctpcType
--   ObjVar
--    ctpcSecurity
--   ObjVar
--    ctpcInitialBitRate
--   ObjVar
--    ctpcRowStatus
--   ObjVar
--    ctpcState
--   ObjVar
--    ctpcStatEventHistTableSize
--   ObjVar
--    ctpcMgmtSysConnEventHistTableSize

ciscoTpCallMIBComplianceRev4 OBJECT IDENTIFIER ::= { ciscoTpCallMIBCompliances 5 }
-- MODULE-COMPLIANCE
--  Status
--    mandatory
--  Descr
--    The compliance statement for entities which implement the Cisco
--    Telepresence Call MIB.
--  Module
--    >>current<<
--   MandGroup
--    ciscoTpCallInformationGroup
--   MandGroup
--    ciscoTpCallInformationGroupSup1
--   MandGroup
--    ciscoTpCallInformationGroupSup2
--   MandGroup
--    ciscoTpCallStatisticsGroup
--   MandGroup
--    ciscoTpCallStatisticsGroupSup1
--   MandGroup
--    ciscoTpCallStatisticsGroupSup2
--   MandGroup
--    ciscoTpCallStatisticsGroupSup3
--   OptGroup
--    ciscoTpCallConfigurationGroup
--   OptGroup
--    ciscoTpCallEventHistoryGroup
--   OptGroup
--    ciscoTpCallMgmtSysConnEventHistGroup
--   ObjVar
--    ctpcStatNotifyEnable
--   ObjVar
--    ctpcMgmtSysConnNotifyEnable
--   ObjVar
--    ctpcSamplePeriod
--   ObjVar
--    ctpcTableSize
--   ObjVar
--    ctpcType
--   ObjVar
--    ctpcSecurity
--   ObjVar
--    ctpcInitialBitRate
--   ObjVar
--    ctpcRowStatus
--   ObjVar
--    ctpcState
--   ObjVar
--    ctpcStatEventHistTableSize
--   ObjVar
--    ctpcMgmtSysConnEventHistTableSize


END
