-- MIB file created 28-Aug-2009 11:03:55, by
--   SMICng version 2.2.11-beta(PRO)(Solaris), January 20, 2001. Enterprise key cisco.com

CISCO-PORT-QOS-MIB DEFINITIONS ::= BEGIN

-- From file: "CISCO-PORT-QOS-MIB.my"
-- Compile options "4 7 F H N O W 03 06 0B 0G 0N 0T"

IMPORTS
    TruthValue, TimeStamp
            FROM SNMPv2-TC-v1
    ifIndex
            FROM IF-MIB
    vtpVlanIndex
            FROM CISCO-VTP-MIB
    ciscoMgmt
            FROM CISCO-SMI
    Dscp, QosLayer2Cos
            FROM CISCO-QOS-PIB-MIB
    SnmpAdminString
            FROM SNMP-FRAMEWORK-MIB
    Counter, Gauge
            FROM RFC1155-SMI
    OBJECT-TYPE
            FROM RFC-1212;

ciscoPortQosMIB OBJECT IDENTIFIER ::= { ciscoMgmt 189 }
-- MODULE-IDENTITY
--  LastUpdated
--    200809100000Z
--  OrgName
--    Cisco Systems, Inc.
--  ContactInfo
--    Cisco Systems
--    Customer Service    
--    
--    Postal:    170 W. Tasman Drive    
--    San Jose, CA  95134-1706    
--    USA    
--    
--    Tel: +1 800 553-NETS    
--    
--    E-mail: cs-port-qos@cisco.com
--  Descr
--    Cisco PORT QOS MIB - Overview
--    
--    This MIB module is for the management of Cisco's    
--    per port rate-limiting and traffic shaping on L3    
--    switch/Router Platform(s).    
--    
--    Per-port rate-limiting is a traffic control method.    
--    A set of rate limits are applied to the traffic    
--    traversing an interface. Each rate limit has a    
--    configurable action that is taken when rate    
--    limiting criteria is met.    
--    
--    Per-port traffic shaping is a traffic control    
--    method. The user can restrict the amount of traffic    
--    coming out of a physical port. Excess traffic is     
--    buffered within the router/switch to the extent     
--    possible. 
--    
--    A class represents a class of traffic. It is defined 
--    via the specification of the packet matching criteria 
--    that identifies packets that are to belong to the class.
--    
--    Class-default: In addition to user defined classes, 
--    a pre-existing class named 'class-default' exists to 
--    represent all packets that do not match any of the user 
--    defined classes. This class-default exists so that 
--    policies can be defined for this group of packets that 
--    do not match any user defined classes.
--    
--    Actions are individual policies (e.g.: policing) that 
--    can be applied to a traffic class.
--    
--    A policy represents a set of actions that are to be 
--    applied to a set of traffic classes. The policy is 
--    associated with a target (like a port) and the direction 
--    of traffic on that target to which the policy is to be 
--    applied.
--    
--    A hierarchical policy is one in which an entire policy 
--    is directly assigned to a class of traffic. Thus, a 
--    hierarchical policy is a nested policy that contains 
--    a set of the pair of a child-policy and the 
--    traffic-class to which it is applied.
--    
--    DSCP (Differentiated Services Code Point) is the six 
--    most significant bits of the ToS field in a IP packet 
--    header.
--    
--    CoS (Class of Service) is the three bits in the layer 2 
--    header that indicates user priority value assigned to 
--    this packet. 
--    
--    This MIB module also provides per port QoS statistics.
--  RevDate
--    200809100000Z
--  RevDescr
--    Added the following tables:
--    cportQosEgressQueueStatsTable,  
--    cportQosClassEgressStatsTable,  
--    cportQosClassIngressStatsTable,  
--    cportQosDscpStatsTable and  
--    cportQosCosStatsTable.
--    Deprecated ciscoPortQosMIBComplianceRev5  
--    added ciscoPortQosMIBComplianceRev6.
--  RevDate
--    200803050000Z
--  RevDescr
--    Added cportQosVlanInProfPolicyOctets,
--    cportQosVlanOutOfProfPolicyOctets,     
--    cportQosVlanViolateProfPolicyPkts and     
--    cportQosVlanViolateProfPolicyOctets to the     
--    cportQosInVlanStatsTable.
--  RevDate
--    200801090000Z
--  RevDescr
--    Added cportQosInProfPolicyOctets,
--    cportQosOutOfProfPolicyOctets,     
--    cportQosViolateProfPolicyPkts and     
--    cportQosViolateProfPolicyOctets to the     
--    cportQosStatsTable.
--  RevDate
--    200602170000Z
--  RevDescr
--    Added per port per vlan ingress
--    statistics table.
--  RevDate
--    200502230000Z
--  RevDescr
--    Deprecated the cportQosIndexType added the
--    cportQosIndexTypeNew which is read-write.    
--    In addition, added the cportQosInProfPolicyPkts and    
--    cportQosOutOfProfPolicyPkts objects to the    
--    statistic table.
--  RevDate
--    200405200000Z
--  RevDescr
--    Extend per port QoS Statistics table by adding
--    no_change object.
--  RevDate
--    200401300000Z
--  RevDescr
--    Add cos(4) to cportQosIndexType.
--  RevDate
--    200203200000Z
--  RevDescr
--    Add per port QoS Statistics table.
--  RevDate
--    200105150000Z
--  RevDescr
--    Add cportQosRLConfigEnable and cportQosTSConfigEnable
--    and renumber the objects.
--  RevDate
--    200012200000Z
--  RevDescr
--    Initial version of this MIB module.

ciscoPortQosMIBObjects OBJECT IDENTIFIER ::= { ciscoPortQosMIB 1 }
cportQosRLConfig OBJECT IDENTIFIER ::= { ciscoPortQosMIBObjects 1 }
cportQosTSConfig OBJECT IDENTIFIER ::= { ciscoPortQosMIBObjects 2 }
cportQosStatistics OBJECT IDENTIFIER ::= { ciscoPortQosMIBObjects 3 }
ciscoPortQosMIBNotifications OBJECT IDENTIFIER ::= { ciscoPortQosMIB 2 }
ciscoPortQosMIBConformance OBJECT IDENTIFIER ::= { ciscoPortQosMIB 3 }
ciscoPortQosMIBCompliances OBJECT IDENTIFIER ::= { ciscoPortQosMIBConformance 1 }
ciscoPortQosMIBGroups OBJECT IDENTIFIER ::= { ciscoPortQosMIBConformance 2 }

cportQosRLConfigTable OBJECT-TYPE
    SYNTAX SEQUENCE OF CportQosRLConfigEntry
    ACCESS not-accessible
    STATUS mandatory
    DESCRIPTION
        "A table of rate limit configuration entries.
        Rate Limiting is a method of traffic control. It allows    
        a set of rate limits to be configured and applied to    
        packets flowing into/out of an interface to regulate    
        network traffic."
    ::= { cportQosRLConfig 1 }

cportQosRLConfigEntry OBJECT-TYPE
    SYNTAX CportQosRLConfigEntry
    ACCESS not-accessible
    STATUS mandatory
    DESCRIPTION
        "A collection of rate-limit configuration
        objects for a particular interface. Entries     
        in the cportQosRLConfigTable are created and     
        deleted by non-SNMP methods. Creation of these    
        entries is dependent upon configuration of a     
        physical interface. Further, the physical     
        interfaces which are configured for port-qos,    
        can only have these entries.    
        
        The ifIndex in the INDEX clause identifies the    
        interface number for a physical interface."
    INDEX { ifIndex, cportQosRLConfigDirection }
    ::= { cportQosRLConfigTable 1 }

CportQosRLConfigEntry ::= SEQUENCE {
    cportQosRLConfigDirection INTEGER,
    cportQosRLConfigEnable TruthValue,
    cportQosRLConfigRate INTEGER,
    cportQosRLConfigBurstSize INTEGER
    }

cportQosRLConfigDirection OBJECT-TYPE
    SYNTAX INTEGER {
        input(1),
        output(2)
        }
    ACCESS not-accessible
    STATUS mandatory
    DESCRIPTION
        "The direction in which the rate-limit is applied
        to packet:    
                input  statistics of the input packets.    
                output statistics of the output packets."
    ::= { cportQosRLConfigEntry 1 }

cportQosRLConfigEnable OBJECT-TYPE
    SYNTAX TruthValue
--    Rsyntax INTEGER {
--        true(1),
--        false(2)
--        }
    ACCESS read-write
    STATUS mandatory
    DESCRIPTION
        "This indicates the rate-limit is enabled or disabled.
        A value of true(1) indicates the rate-limit is enabled    
        and a value of false(2) indicates it's disabled.    
        Writing a value of true(1) to this object also     
        requires writing a valid value to the      
        cportQosRLConfigRate at the same time.     
        Writing to cportQosRLConfigBurstSize is optional."
    ::= { cportQosRLConfigEntry 2 }

cportQosRLConfigRate OBJECT-TYPE
    SYNTAX INTEGER(32000..2147483647)
--  Units
--    bits per second
    ACCESS read-write
    STATUS mandatory
    DESCRIPTION
        "This is the sustained rate permitted by the rate
        limit.    
        Writing to this object also requires writing a value of    
        true(1) to cportQosRLConfigEnable at the same time."
    ::= { cportQosRLConfigEntry 3 }

cportQosRLConfigBurstSize OBJECT-TYPE
    SYNTAX INTEGER(0..64000)
--  Units
--    bytes
    ACCESS read-write
    STATUS mandatory
    DESCRIPTION
        "The burst size.  The amount of traffic, in bytes,
        in excess of the sustained rate which will be    
        instantaneously permitted by the rate limit.    
        Writing to this object also requires writing a value     
        of true(1) to cportQosRLConfigEnable and a valid value    
        to the cportQosRLConfigRate at the same time."
    ::= { cportQosRLConfigEntry 4 }

cportQosTSConfigTable OBJECT-TYPE
    SYNTAX SEQUENCE OF CportQosTSConfigEntry
    ACCESS not-accessible
    STATUS mandatory
    DESCRIPTION
        "A table of traffic-shaping action configuration
        entries."
    ::= { cportQosTSConfig 1 }

cportQosTSConfigEntry OBJECT-TYPE
    SYNTAX CportQosTSConfigEntry
    ACCESS not-accessible
    STATUS mandatory
    DESCRIPTION
        "A collection of traffic shaping action
        configuration objects for a particular interface.    
        Entries in the cportQosTSConfigTable are created    
        and deleted by non-SNMP methods. Creation of these    
        entries is dependent upon configuration of a    
        physical interface. Further, the physical interfaces    
        which are configured for port-qos, can only have     
        these entries.    
        
        The ifIndex in the INDEX clause identifies the    
        interface number for a physical interface."
    INDEX { ifIndex }
    ::= { cportQosTSConfigTable 1 }

CportQosTSConfigEntry ::= SEQUENCE {
    cportQosTSConfigEnable TruthValue,
    cportQosTSConfigRate INTEGER,
    cportQosTSConfigBurstSize INTEGER
    }

cportQosTSConfigEnable OBJECT-TYPE
    SYNTAX TruthValue
--    Rsyntax INTEGER {
--        true(1),
--        false(2)
--        }
    ACCESS read-write
    STATUS mandatory
    DESCRIPTION
        "This indicates the traffic shaping is enabled or
        disabled. A value of true(1) indicates the traffic    
        shaping is enabled and a value of false(2) indicates     
        it's disabled.    
        Writing a value of true(1) to this object also     
        requires writing a valid value to the      
        cportQosTSConfigRate at the same time.     
        Writing to cportQosTSConfigBurstSize is optional."
    ::= { cportQosTSConfigEntry 1 }

cportQosTSConfigRate OBJECT-TYPE
    SYNTAX INTEGER(32000..2147483647)
--  Units
--    bits per second
    ACCESS read-write
    STATUS mandatory
    DESCRIPTION
        "This is the sustained rate permitted by the
        traffic shaping. Writing to this object also    
        requires writing a value of true(1) to     
        cportQosTSConfigEnable at the same time."
    ::= { cportQosTSConfigEntry 2 }

cportQosTSConfigBurstSize OBJECT-TYPE
    SYNTAX INTEGER(0..512000)
--  Units
--    bits
    ACCESS read-write
    STATUS mandatory
    DESCRIPTION
        "The amount of traffic, in bits, in excess
        of the sustained traffic shaping rate that    
        will be instantaneously permitted by this feature.    
        Writing to this object also requires writing a value     
        of true(1) to cportQosTSConfigEnable and a valid value    
        to the cportQosTSConfigRate at the same time."
    ::= { cportQosTSConfigEntry 3 }

cportQosIndexType OBJECT-TYPE
    SYNTAX INTEGER {
        none(1),
        dscp(2),
        ipPrecedence(3),
        cos(4)
        }
    ACCESS read-only
    STATUS deprecated
    DESCRIPTION
        "This object specifies the sorting mechanism used to
        collect and store the statistical QoS information.      
        This object value is device dependent and it could be    
        optionally configured via command-line.    
        
        This object has been deprecated in order to make the    
        selection of sorting mechanism selectable from the    
        MIB. The replacement object is cportQosIndexTypeNew."
    ::= { cportQosStatistics 1 }

cportQosStatsTable OBJECT-TYPE
    SYNTAX SEQUENCE OF CportQosStatsEntry
    ACCESS not-accessible
    STATUS mandatory
    DESCRIPTION
        "This table specifies QoS port related Statistical
        information."
    ::= { cportQosStatistics 2 }

cportQosStatsEntry OBJECT-TYPE
    SYNTAX CportQosStatsEntry
    ACCESS not-accessible
    STATUS mandatory
    DESCRIPTION
        "Each entry in this table describes the QoS port
        statistical information which are : pre/post policy     
        pkts/octets counts, drop pkts/octets,     
        classified pkts/octets."
    INDEX { ifIndex, cportQosDirection, cportQosIndex }
    ::= { cportQosStatsTable 1 }

CportQosStatsEntry ::= SEQUENCE {
    cportQosDirection INTEGER,
    cportQosIndex Gauge,
    cportQosPrePolicyPkts Counter,
    cportQosPrePolicyOctets Counter,
    cportQosPostPolicyPkts Counter,
    cportQosPostPolicyOctets Counter,
    cportQosDropPkts Counter,
    cportQosDropOctets Counter,
    cportQosClassifiedOctets Counter,
    cportQosClassifiedPkts Counter,
    cportQosNoChangePkts Counter,
    cportQosNoChangeOctets Counter,
    cportQosInProfPolicyPkts Counter,
    cportQosOutOfProfPolicyPkts Counter,
    cportQosInProfPolicyOctets Counter,
    cportQosOutOfProfPolicyOctets Counter,
    cportQosViolateProfPolicyPkts Counter,
    cportQosViolateProfPolicyOctets Counter
    }

cportQosDirection OBJECT-TYPE
    SYNTAX INTEGER {
        ingress(1),
        egress(2)
        }
    ACCESS not-accessible
    STATUS mandatory
    DESCRIPTION
        "The direction of the reported statistics:
        -'ingress' statistics for the input direction.    
        -'egress' statistics for the output direction."
    ::= { cportQosStatsEntry 1 }

cportQosIndex OBJECT-TYPE
    SYNTAX Gauge
    ACCESS not-accessible
    STATUS mandatory
    DESCRIPTION
        "An arbitrary integer to identify this entry.
        cportQosIndex value, which may have non-contiguous    
        range, is linked to cportQosIndexType:    
        
         -if cportQosIndexTypeNew equals 'none', cportQosIndex     
          is constant with the value of 1 and all statistics    
          are classified per port    
        
         -if cportQosIndexTypeNew equals 'DSCP', cportQosIndex    
          range is from 1 to 65 and all statistics are    
          classified per port and DSCP value.  The range    
          of DSCP values reported is shifted up one meaning     
          a cportQosIndex of 1 translates to a packet DSCP    
          value of 0.    
          Value of 65 is an arbitrary number used to report    
          aggregate counts of packets which were not displayed    
          in the 1 to 64 range.  This usually happens when the    
          range value of cportQosIndex is non-contiguous    
        
         -if cportQosIndexTypeNew equals 'ipPrecedence',     
          cportQosIndex range is from 1 to 8 and all    
          statistics are classified per port and IP precedence    
          value.  The range of IP precedence values reported    
          is shifted up one meaning a cportQosIndex of 1    
          translates to an IP precedence value of 0    
        
         -if cportQosIndexTypeNew equals 'cos',     
          cportQosIndex range is from 1 to 8 and all    
          statistics are classified per interface and L2 COS    
          value.  The range of COS values reported    
          is shifted up one meaning a cportQosIndex of 1    
          translates to a COS value of 0    
        
         -if cportQosIndexTypeNew equals 'police',     
          cportQosIndex range is from 1 to 65 and all    
          statistics are classified per interface and police    
          index.     
          The police indexes are arbitrary numbers that do    
          not correlate to policers names or identifiers."
    ::= { cportQosStatsEntry 2 }

cportQosPrePolicyPkts OBJECT-TYPE
    SYNTAX --?? syntax is not convertable to SMIv1
           Counter
--  Units
--    packets
    ACCESS read-only
    STATUS mandatory
    DESCRIPTION
        "The count of packets prior to executing any QoS
        policies."
    ::= { cportQosStatsEntry 3 }

cportQosPrePolicyOctets OBJECT-TYPE
    SYNTAX --?? syntax is not convertable to SMIv1
           Counter
--  Units
--    octets
    ACCESS read-only
    STATUS mandatory
    DESCRIPTION
        "The count of octets prior to executing any QoS
        policies."
    ::= { cportQosStatsEntry 4 }

cportQosPostPolicyPkts OBJECT-TYPE
    SYNTAX --?? syntax is not convertable to SMIv1
           Counter
--  Units
--    packets
    ACCESS read-only
    STATUS mandatory
    DESCRIPTION
        "The count of packets after executing QoS policies."
    ::= { cportQosStatsEntry 5 }

cportQosPostPolicyOctets OBJECT-TYPE
    SYNTAX --?? syntax is not convertable to SMIv1
           Counter
--  Units
--    octets
    ACCESS read-only
    STATUS mandatory
    DESCRIPTION
        "The count of octets after executing QoS policies."
    ::= { cportQosStatsEntry 6 }

cportQosDropPkts OBJECT-TYPE
    SYNTAX --?? syntax is not convertable to SMIv1
           Counter
--  Units
--    packets
    ACCESS read-only
    STATUS mandatory
    DESCRIPTION
        "The count of dropped packets as the result of
        queuing and scheduling related QoS features that    
        can produce drops."
    ::= { cportQosStatsEntry 7 }

cportQosDropOctets OBJECT-TYPE
    SYNTAX --?? syntax is not convertable to SMIv1
           Counter
--  Units
--    octets
    ACCESS read-only
    STATUS mandatory
    DESCRIPTION
        "The count of dropped octets as the result of
        queuing and scheduling related QoS features that    
        can produce drops."
    ::= { cportQosStatsEntry 8 }

cportQosClassifiedOctets OBJECT-TYPE
    SYNTAX --?? syntax is not convertable to SMIv1
           Counter
--  Units
--    octets
    ACCESS read-only
    STATUS mandatory
    DESCRIPTION
        "The count of classified octets during QoS."
    ::= { cportQosStatsEntry 9 }

cportQosClassifiedPkts OBJECT-TYPE
    SYNTAX --?? syntax is not convertable to SMIv1
           Counter
--  Units
--    packets
    ACCESS read-only
    STATUS mandatory
    DESCRIPTION
        "The count of classified packets during QoS."
    ::= { cportQosStatsEntry 10 }

cportQosNoChangePkts OBJECT-TYPE
    SYNTAX --?? syntax is not convertable to SMIv1
           Counter
--  Units
--    packets
    ACCESS read-only
    STATUS mandatory
    DESCRIPTION
        "The count of packets maintain unchange after
        executing QoS policies."
    ::= { cportQosStatsEntry 11 }

cportQosNoChangeOctets OBJECT-TYPE
    SYNTAX --?? syntax is not convertable to SMIv1
           Counter
--  Units
--    octets
    ACCESS read-only
    STATUS mandatory
    DESCRIPTION
        "The count of octets maintain unchange after
        executing QoS policies."
    ::= { cportQosStatsEntry 12 }

cportQosInProfPolicyPkts OBJECT-TYPE
    SYNTAX --?? syntax is not convertable to SMIv1
           Counter
--  Units
--    packets
    ACCESS read-only
    STATUS mandatory
    DESCRIPTION
        "The count of packets that are within the policer
        profile limit configured for this policy."
    ::= { cportQosStatsEntry 13 }

cportQosOutOfProfPolicyPkts OBJECT-TYPE
    SYNTAX --?? syntax is not convertable to SMIv1
           Counter
--  Units
--    packets
    ACCESS read-only
    STATUS mandatory
    DESCRIPTION
        "The count of packets that exceed the policer
        profile limit configured for this policy."
    ::= { cportQosStatsEntry 14 }

cportQosInProfPolicyOctets OBJECT-TYPE
    SYNTAX --?? syntax is not convertable to SMIv1
           Counter
--  Units
--    octets
    ACCESS read-only
    STATUS mandatory
    DESCRIPTION
        "The count of octets that are within the policer
        profile limit configured for this policy."
    ::= { cportQosStatsEntry 15 }

cportQosOutOfProfPolicyOctets OBJECT-TYPE
    SYNTAX --?? syntax is not convertable to SMIv1
           Counter
--  Units
--    octets
    ACCESS read-only
    STATUS mandatory
    DESCRIPTION
        "The count of octets that exceed the policer
        profile limit configured for this policy."
    ::= { cportQosStatsEntry 16 }

cportQosViolateProfPolicyPkts OBJECT-TYPE
    SYNTAX --?? syntax is not convertable to SMIv1
           Counter
--  Units
--    packets
    ACCESS read-only
    STATUS mandatory
    DESCRIPTION
        "The count of packets that violate the policer
        profile limit configured for this policy."
    ::= { cportQosStatsEntry 17 }

cportQosViolateProfPolicyOctets OBJECT-TYPE
    SYNTAX --?? syntax is not convertable to SMIv1
           Counter
--  Units
--    octets
    ACCESS read-only
    STATUS mandatory
    DESCRIPTION
        "The count of octets that violate the policer
        profile limit configured for this policy."
    ::= { cportQosStatsEntry 18 }

cportQosIndexTypeNew OBJECT-TYPE
    SYNTAX INTEGER {
        none(1),
        dscp(2),
        ipPrecedence(3),
        cos(4),
        police(5)
        }
    ACCESS read-write
    STATUS mandatory
    DESCRIPTION
        "This object specifies the sorting mechanism used to
        collect and store the statistical QoS information.      
        This object value is device dependent."
    ::= { cportQosStatistics 3 }

cportQosInVlanStatsTable OBJECT-TYPE
    SYNTAX SEQUENCE OF CportQosInVlanStatsEntry
    ACCESS not-accessible
    STATUS mandatory
    DESCRIPTION
        "This table specifies QoS port related ingress
        statistical information. The type of information     
        is controlled by the cportQosIndexTypeNew object."
    ::= { cportQosStatistics 4 }

cportQosInVlanStatsEntry OBJECT-TYPE
    SYNTAX CportQosInVlanStatsEntry
    ACCESS not-accessible
    STATUS mandatory
    DESCRIPTION
        "It exists an entry in this table for each port
        on which QoS is configured per port and per VLAN."
    INDEX { ifIndex, vtpVlanIndex, cportQosIndex }
    ::= { cportQosInVlanStatsTable 1 }

CportQosInVlanStatsEntry ::= SEQUENCE {
    cportQosVlanInProfPolicyPkts Counter,
    cportQosVlanOutOfProfPolicyPkts Counter,
    cportQosVlanInProfPolicyOctets Counter,
    cportQosVlanOutOfProfPolicyOctets Counter,
    cportQosVlanViolateProfPolicyPkts Counter,
    cportQosVlanViolateProfPolicyOctets Counter
    }

cportQosVlanInProfPolicyPkts OBJECT-TYPE
    SYNTAX --?? syntax is not convertable to SMIv1
           Counter
--  Units
--    packets
    ACCESS read-only
    STATUS mandatory
    DESCRIPTION
        "The count of packets that are within the policer
        profile limit configured for this policy."
    ::= { cportQosInVlanStatsEntry 1 }

cportQosVlanOutOfProfPolicyPkts OBJECT-TYPE
    SYNTAX --?? syntax is not convertable to SMIv1
           Counter
--  Units
--    packets
    ACCESS read-only
    STATUS mandatory
    DESCRIPTION
        "The count of packets that exceeds the policer
        profile limit configured for this policy."
    ::= { cportQosInVlanStatsEntry 2 }

cportQosVlanInProfPolicyOctets OBJECT-TYPE
    SYNTAX --?? syntax is not convertable to SMIv1
           Counter
--  Units
--    octets
    ACCESS read-only
    STATUS mandatory
    DESCRIPTION
        "The count of octets that are within the policer
        profile limit configured for this policy."
    ::= { cportQosInVlanStatsEntry 3 }

cportQosVlanOutOfProfPolicyOctets OBJECT-TYPE
    SYNTAX --?? syntax is not convertable to SMIv1
           Counter
--  Units
--    octets
    ACCESS read-only
    STATUS mandatory
    DESCRIPTION
        "The count of octets that exceed the policer
        profile limit configured for this policy."
    ::= { cportQosInVlanStatsEntry 4 }

cportQosVlanViolateProfPolicyPkts OBJECT-TYPE
    SYNTAX --?? syntax is not convertable to SMIv1
           Counter
--  Units
--    packets
    ACCESS read-only
    STATUS mandatory
    DESCRIPTION
        "The count of packets that violate the policer
        profile limit configured for this policy."
    ::= { cportQosInVlanStatsEntry 5 }

cportQosVlanViolateProfPolicyOctets OBJECT-TYPE
    SYNTAX --?? syntax is not convertable to SMIv1
           Counter
--  Units
--    octets
    ACCESS read-only
    STATUS mandatory
    DESCRIPTION
        "The count of octets that violate the policer
        profile limit configured for this policy."
    ::= { cportQosInVlanStatsEntry 6 }

cportQosEgressQueueStatsTable OBJECT-TYPE
    SYNTAX SEQUENCE OF CportQosEgressQueueStatsEntry
    ACCESS not-accessible
    STATUS mandatory
    DESCRIPTION
        "This table specifies QoS related statistical
        information for egress queues on each port.   
        The agent will add an entry in this table for each 
        queue, threshold and port."
    ::= { cportQosStatistics 5 }

cportQosEgressQueueStatsEntry OBJECT-TYPE
    SYNTAX CportQosEgressQueueStatsEntry
    ACCESS not-accessible
    STATUS mandatory
    DESCRIPTION
        "A conceptual row in cportQosEgressQueueStatsTable."
    INDEX { ifIndex, cportQosQueueId, cportQosQueueThreshold }
    ::= { cportQosEgressQueueStatsTable 1 }

CportQosEgressQueueStatsEntry ::= SEQUENCE {
    cportQosQueueId Gauge,
    cportQosQueueThreshold Gauge,
    cportQosQueueEnqueuePkts Counter,
    cportQosQueueDropPkts Counter
    }

cportQosQueueId OBJECT-TYPE
    SYNTAX Gauge(1..2147483647)
    ACCESS not-accessible
    STATUS mandatory
    DESCRIPTION
        "This object identifies the queue ID of this port for
        which QoS statistics are collected. 
        
        For example, if a port has 4 queues, this index value
        can be 1,2,3,4."
    ::= { cportQosEgressQueueStatsEntry 1 }

cportQosQueueThreshold OBJECT-TYPE
    SYNTAX Gauge(1..2147483647)
    ACCESS not-accessible
    STATUS mandatory
    DESCRIPTION
        "This object identifies the threshold number 
        of the queue threshold associated with this
        queue. A queue can have more than one threshold.
        
        For example, if a queue has 3 thresholds, this index
        could be 1,2,3."
    ::= { cportQosEgressQueueStatsEntry 2 }

cportQosQueueEnqueuePkts OBJECT-TYPE
    SYNTAX --?? syntax is not convertable to SMIv1
           Counter
--  Units
--    Packets
    ACCESS read-only
    STATUS mandatory
    DESCRIPTION
        "This object indicates the number of egress packets
        that have been enqueued for this queue and threshold."
    ::= { cportQosEgressQueueStatsEntry 3 }

cportQosQueueDropPkts OBJECT-TYPE
    SYNTAX --?? syntax is not convertable to SMIv1
           Counter
--  Units
--    Packets
    ACCESS read-only
    STATUS mandatory
    DESCRIPTION
        "This object indicates the number of egress packets
        that have been dropped for this queue and threshold."
    ::= { cportQosEgressQueueStatsEntry 4 }

cportQosClassEgressStatsTable OBJECT-TYPE
    SYNTAX SEQUENCE OF CportQosClassEgressStatsEntry
    ACCESS not-accessible
    STATUS mandatory
    DESCRIPTION
        "This table specifies egress QoS related statistical
        information for classes associated with an egress QoS 
        policy. Each queue on a port is uniquely mapped to a  
        class in an egress QoS policy. This table provides 
        the statistical information for each class-queue
        on each port. 
        
        The agent will add an entry in this table for each 
        queue and threshold on a port associated with a class."
    ::= { cportQosStatistics 6 }

cportQosClassEgressStatsEntry OBJECT-TYPE
    SYNTAX CportQosClassEgressStatsEntry
    ACCESS not-accessible
    STATUS mandatory
    DESCRIPTION
        "A conceptual row in cportQosClassEgressStatsTable."
    INDEX { ifIndex, cportQosClassId, cportQosClassThreshold }
    ::= { cportQosClassEgressStatsTable 1 }

CportQosClassEgressStatsEntry ::= SEQUENCE {
    cportQosClassId Gauge,
    cportQosClassThreshold Gauge,
    cportQosClassName SnmpAdminString,
    cportQosClassEnqueuePkts Counter,
    cportQosClassDropPkts Counter,
    cportQosClassDiscontinuityTime TimeStamp
    }

cportQosClassId OBJECT-TYPE
    SYNTAX Gauge(0..2147483647)
    ACCESS not-accessible
    STATUS mandatory
    DESCRIPTION
        "This object identifies the class-ID of the class in
        an egress policy for which QoS statistics are being 
        collected.
        
        Each queue on a port is uniquely mapped to a class 
        in an egress policy. Each class in a policy is 
        uniquely identified by a class-ID. A value of 0 
        indicates the default queue/class-default."
    ::= { cportQosClassEgressStatsEntry 1 }

cportQosClassThreshold OBJECT-TYPE
    SYNTAX Gauge(1..2147483647)
--  Units
--    Number of buffers
    ACCESS not-accessible
    STATUS mandatory
    DESCRIPTION
        "This object identifies the tail-drop queue thresholds
        value on a class-queue on a port. These values can
        either be the default value or each could be an 
        explicitly configured value. 
        
        For example, if a queue has 3 thresholds, 16, 64 and 256, 
        this index value for each threshold would be 16, 64, 
        256 respectively."
    ::= { cportQosClassEgressStatsEntry 2 }

cportQosClassName OBJECT-TYPE
    SYNTAX SnmpAdminString
--    Rsyntax OCTET STRING(SIZE(0..255))
    ACCESS read-only
    STATUS mandatory
    DESCRIPTION
        "This object indicates the class name that is associated
        with the class-ID indicated by the cportQosClassId 
        object."
    ::= { cportQosClassEgressStatsEntry 3 }

cportQosClassEnqueuePkts OBJECT-TYPE
    SYNTAX --?? syntax is not convertable to SMIv1
           Counter
--  Units
--    Packets
    ACCESS read-only
    STATUS mandatory
    DESCRIPTION
        "This object indicates the number of egress packets
        that have been enqueued for this queue and threshold."
    ::= { cportQosClassEgressStatsEntry 4 }

cportQosClassDropPkts OBJECT-TYPE
    SYNTAX --?? syntax is not convertable to SMIv1
           Counter
--  Units
--    Packets
    ACCESS read-only
    STATUS mandatory
    DESCRIPTION
        "This object indicates the number of egress packets
        that have been dropped for this queue and threshold."
    ::= { cportQosClassEgressStatsEntry 5 }

cportQosClassDiscontinuityTime OBJECT-TYPE
    SYNTAX TimeStamp
--    Rsyntax TimeTicks
    ACCESS read-only
    STATUS mandatory
    DESCRIPTION
        "The value of sysUpTime on the most recent occasion
        at which any of this entry's counter experienced a 
        discontinuity. If discontinuities have not occurred 
        since the last re-initialization of the local 
        management subsystem, then this object contains a 
        zero value."
    ::= { cportQosClassEgressStatsEntry 6 }

cportQosClassIngressStatsTable OBJECT-TYPE
    SYNTAX SEQUENCE OF CportQosClassIngressStatsEntry
    ACCESS not-accessible
    STATUS mandatory
    DESCRIPTION
        "This table specifies QoS related statistical
        information per port for ingress traffic belonging to
        QoS classes configured with an action that support
        statistics (for example: a policer)."
    ::= { cportQosStatistics 7 }

cportQosClassIngressStatsEntry OBJECT-TYPE
    SYNTAX CportQosClassIngressStatsEntry
    ACCESS not-accessible
    STATUS mandatory
    DESCRIPTION
        "A conceptual row in cportQosClassIngressStatsTable.
        An entry is added per port for ingress traffic belonging
        to QoS classes, indicated by cportQosClassIdLevel1 and
        cportQosClassIdLevel2, configured with an action that
        supports statistics."
    INDEX { ifIndex, cportQosClassIdLevel1, cportQosClassIdLevel2 }
    ::= { cportQosClassIngressStatsTable 1 }

CportQosClassIngressStatsEntry ::= SEQUENCE {
    cportQosClassIdLevel1 Gauge,
    cportQosClassIdLevel2 Gauge,
    cportQosClassNameLevel1 SnmpAdminString,
    cportQosClassNameLevel2 SnmpAdminString,
    cportQosPoliceConformPkts Counter,
    cportQosPoliceConformOctets Counter,
    cportQosPoliceExceedPkts Counter,
    cportQosPoliceExceedOctets Counter,
    cportQosPoliceViolatePkts Counter,
    cportQosPoliceViolateOctets Counter,
    cportQosPoliceConformRate Gauge,
    cportQosPoliceExceedRate Gauge,
    cportQosPoliceViolateRate Gauge,
    cportQosPoliceDiscontinuityTime TimeStamp
    }

cportQosClassIdLevel1 OBJECT-TYPE
    SYNTAX Gauge(0..2147483647)
    ACCESS not-accessible
    STATUS mandatory
    DESCRIPTION
        "This object identifies the class-ID of a class at the
        first (highest) level of a hierarchical policy. A value
        of  0 indicates class default. For a non-hierarchical
        policy, the value of this object is always 0."
    ::= { cportQosClassIngressStatsEntry 1 }

cportQosClassIdLevel2 OBJECT-TYPE
    SYNTAX Gauge(0..2147483647)
    ACCESS not-accessible
    STATUS mandatory
    DESCRIPTION
        "This object identifies the class-ID of a class at the
        second level of a hierarchical policy, or at the first
        (only) level in a non-hierarchical policy. For a two 
        level policy, this object identifies the class-ID at the  
        second level of the policy. For a non-hierarchical/
        single level policy this object identifies the class-ID
        of a class at the first (only) level of the policy. A
        value of 0 indicates class default."
    ::= { cportQosClassIngressStatsEntry 2 }

cportQosClassNameLevel1 OBJECT-TYPE
    SYNTAX SnmpAdminString
--    Rsyntax OCTET STRING(SIZE(0..255))
    ACCESS read-only
    STATUS mandatory
    DESCRIPTION
        "This object indicates the class name that is associated
        with the class-ID indicated by the cportQosClassIdLevel1 
        object."
    ::= { cportQosClassIngressStatsEntry 3 }

cportQosClassNameLevel2 OBJECT-TYPE
    SYNTAX SnmpAdminString
--    Rsyntax OCTET STRING(SIZE(0..255))
    ACCESS read-only
    STATUS mandatory
    DESCRIPTION
        "This object indicates the class name that is associated
        with the class-ID indicated by the cportQosClassIdLevel2 
        object."
    ::= { cportQosClassIngressStatsEntry 4 }

cportQosPoliceConformPkts OBJECT-TYPE
    SYNTAX --?? syntax is not convertable to SMIv1
           Counter
--  Units
--    Packets
    ACCESS read-only
    STATUS mandatory
    DESCRIPTION
        "This object indicates the number of ingress packets
        that conforms to the policing rate for traffic belonging 
        to the classes indicated by the cportQosClassIdLevel1 
        and cportQosClassIdLevel2 indices."
    ::= { cportQosClassIngressStatsEntry 5 }

cportQosPoliceConformOctets OBJECT-TYPE
    SYNTAX --?? syntax is not convertable to SMIv1
           Counter
--  Units
--    Octets
    ACCESS read-only
    STATUS mandatory
    DESCRIPTION
        "This object indicates the number of ingress octets
        that conforms to the policing rate for traffic belonging 
        to the classes indicated by the cportQosClassIdLevel1 
        and cportQosClassIdLevel2 indices."
    ::= { cportQosClassIngressStatsEntry 6 }

cportQosPoliceExceedPkts OBJECT-TYPE
    SYNTAX --?? syntax is not convertable to SMIv1
           Counter
--  Units
--    Packets
    ACCESS read-only
    STATUS mandatory
    DESCRIPTION
        "This object indicates the number of ingress packets
        that exceeds the policing rate for traffic belonging 
        to the classes indicated by the cportQosClassIdLevel1 
        and cportQosClassIdLevel2 indices."
    ::= { cportQosClassIngressStatsEntry 7 }

cportQosPoliceExceedOctets OBJECT-TYPE
    SYNTAX --?? syntax is not convertable to SMIv1
           Counter
--  Units
--    Octets
    ACCESS read-only
    STATUS mandatory
    DESCRIPTION
        "This object indicates the number of ingress octets
        that exceeds the policing rate for traffic belonging 
        to the classes indicated by the cportQosClassIdLevel1 
        and cportQosClassIdLevel2 indices."
    ::= { cportQosClassIngressStatsEntry 8 }

cportQosPoliceViolatePkts OBJECT-TYPE
    SYNTAX --?? syntax is not convertable to SMIv1
           Counter
--  Units
--    Packets
    ACCESS read-only
    STATUS mandatory
    DESCRIPTION
        "This object indicates the number of ingress packets
        that violates the policing rate for traffic belonging 
        to the classes indicated by the cportQosClassIdLevel1 
        and cportQosClassIdLevel2 indices."
    ::= { cportQosClassIngressStatsEntry 9 }

cportQosPoliceViolateOctets OBJECT-TYPE
    SYNTAX --?? syntax is not convertable to SMIv1
           Counter
--  Units
--    Octets
    ACCESS read-only
    STATUS mandatory
    DESCRIPTION
        "This object indicates the number of ingress octets
        that violates the policing rate for traffic belonging 
        to the classes indicated by the cportQosClassIdLevel1 
        and cportQosClassIdLevel2 indices."
    ::= { cportQosClassIngressStatsEntry 10 }

cportQosPoliceConformRate OBJECT-TYPE
    SYNTAX Gauge
--  Units
--    bits per second
    ACCESS read-only
    STATUS mandatory
    DESCRIPTION
        "This object indicates the rate of ingress packets
        that conforms to the policing rate for traffic belonging
        to the classes indicated by the cportQosClassIdLevel1 
        and cportQosClassIdLevel2 indices."
    ::= { cportQosClassIngressStatsEntry 11 }

cportQosPoliceExceedRate OBJECT-TYPE
    SYNTAX Gauge
--  Units
--    bits per second
    ACCESS read-only
    STATUS mandatory
    DESCRIPTION
        "This object indicates the rate of ingress packets
        that exceeds the policing for traffic belonging to
        the classes indicated by the cportQosClassIdLevel1 
        and cportQosClassIdLevel2 indices."
    ::= { cportQosClassIngressStatsEntry 12 }

cportQosPoliceViolateRate OBJECT-TYPE
    SYNTAX Gauge
--  Units
--    bits per second
    ACCESS read-only
    STATUS mandatory
    DESCRIPTION
        "This object indicates the rate of ingress packets
        that violates the policing for traffic belonging to
        the classes indicated by the cportQosClassIdLevel1 
        and cportQosClassIdLevel2 indices."
    ::= { cportQosClassIngressStatsEntry 13 }

cportQosPoliceDiscontinuityTime OBJECT-TYPE
    SYNTAX TimeStamp
--    Rsyntax TimeTicks
    ACCESS read-only
    STATUS mandatory
    DESCRIPTION
        "The value of sysUpTime on the most recent occasion
        at which any of this entry's counter experienced a 
        discontinuity. If discontinuities have not occurred 
        since the last re-initialization of the local 
        management subsystem, then this object contains a 
        zero value."
    ::= { cportQosClassIngressStatsEntry 14 }

cportQosDscpStatsTable OBJECT-TYPE
    SYNTAX SEQUENCE OF CportQosDscpStatsEntry
    ACCESS not-accessible
    STATUS mandatory
    DESCRIPTION
        "This table indicates QoS related statistical
        DSCP information. The statistics are collected   
        per physical port and DSCP value."
    ::= { cportQosStatistics 8 }

cportQosDscpStatsEntry OBJECT-TYPE
    SYNTAX CportQosDscpStatsEntry
    ACCESS not-accessible
    STATUS mandatory
    DESCRIPTION
        "A conceptual row in cportQosDscpStatsTable. There is
        an entry in this table for each port and each DSCP  
        value."
    INDEX { ifIndex, cportQosDscpValue }
    ::= { cportQosDscpStatsTable 1 }

CportQosDscpStatsEntry ::= SEQUENCE {
    cportQosDscpValue Dscp,
    cportQosDscpIngressPkts Counter,
    cportQosDscpIngressOctets Counter,
    cportQosDscpEgressPkts Counter,
    cportQosDscpEgressOctets Counter
    }

cportQosDscpValue OBJECT-TYPE
    SYNTAX Dscp
--    Rsyntax INTEGER(0..63)
    ACCESS not-accessible
    STATUS mandatory
    DESCRIPTION
        "This object identifies the DSCP value for
        incoming or outgoing packets."
    ::= { cportQosDscpStatsEntry 1 }

cportQosDscpIngressPkts OBJECT-TYPE
    SYNTAX --?? syntax is not convertable to SMIv1
           Counter
--  Units
--    Packets
    ACCESS read-only
    STATUS mandatory
    DESCRIPTION
        "This object indicates the number of ingress packets
        whose DSCP value matched the value of the 
        cportQosDscpValue object."
    ::= { cportQosDscpStatsEntry 2 }

cportQosDscpIngressOctets OBJECT-TYPE
    SYNTAX --?? syntax is not convertable to SMIv1
           Counter
--  Units
--    Octets
    ACCESS read-only
    STATUS mandatory
    DESCRIPTION
        "This object indicates the number of ingress octets
        whose DSCP value matched the value of the 
        cportQosDscpValue object."
    ::= { cportQosDscpStatsEntry 3 }

cportQosDscpEgressPkts OBJECT-TYPE
    SYNTAX --?? syntax is not convertable to SMIv1
           Counter
--  Units
--    Packets
    ACCESS read-only
    STATUS mandatory
    DESCRIPTION
        "This object indicates the number of egress packets
        whose DSCP value matched the value of the 
        cportQosDscpValue object."
    ::= { cportQosDscpStatsEntry 4 }

cportQosDscpEgressOctets OBJECT-TYPE
    SYNTAX --?? syntax is not convertable to SMIv1
           Counter
--  Units
--    Octets
    ACCESS read-only
    STATUS mandatory
    DESCRIPTION
        "This object indicates the number of egress octets
        whose DSCP value matched the value of the 
        cportQosDscpValue object."
    ::= { cportQosDscpStatsEntry 5 }

cportQosCosStatsTable OBJECT-TYPE
    SYNTAX SEQUENCE OF CportQosCosStatsEntry
    ACCESS not-accessible
    STATUS mandatory
    DESCRIPTION
        "This table indicates QoS related statistical
        COS information. The statistics are collected   
        per  physical port and COS value."
    ::= { cportQosStatistics 9 }

cportQosCosStatsEntry OBJECT-TYPE
    SYNTAX CportQosCosStatsEntry
    ACCESS not-accessible
    STATUS mandatory
    DESCRIPTION
        "A conceptual row in cportQosCosStatsTable. There is
        an entry in this table for each port and each COS  
        value."
    INDEX { ifIndex, cportQosCosValue }
    ::= { cportQosCosStatsTable 1 }

CportQosCosStatsEntry ::= SEQUENCE {
    cportQosCosValue QosLayer2Cos,
    cportQosCosIngressPkts Counter,
    cportQosCosIngressOctets Counter,
    cportQosCosEgressPkts Counter,
    cportQosCosEgressOctets Counter
    }

cportQosCosValue OBJECT-TYPE
    SYNTAX QosLayer2Cos
--    Rsyntax INTEGER(0..7)
    ACCESS not-accessible
    STATUS mandatory
    DESCRIPTION
        "This object identifies the COS value for
        each received or sent packet."
    ::= { cportQosCosStatsEntry 1 }

cportQosCosIngressPkts OBJECT-TYPE
    SYNTAX --?? syntax is not convertable to SMIv1
           Counter
--  Units
--    Packets
    ACCESS read-only
    STATUS mandatory
    DESCRIPTION
        "This object indicates the number of ingress
        packets whose COS value matched the value of the 
        cportQosCosValue object."
    ::= { cportQosCosStatsEntry 2 }

cportQosCosIngressOctets OBJECT-TYPE
    SYNTAX --?? syntax is not convertable to SMIv1
           Counter
--  Units
--    Octets
    ACCESS read-only
    STATUS mandatory
    DESCRIPTION
        "This object indicates the number of ingress
        octets whose COS value matched the value of the 
        cportQosCosValue object."
    ::= { cportQosCosStatsEntry 3 }

cportQosCosEgressPkts OBJECT-TYPE
    SYNTAX --?? syntax is not convertable to SMIv1
           Counter
--  Units
--    Packets
    ACCESS read-only
    STATUS mandatory
    DESCRIPTION
        "This object indicates the number of egress
        packets whose COS value matched the value of the 
        cportQosCosValue object."
    ::= { cportQosCosStatsEntry 4 }

cportQosCosEgressOctets OBJECT-TYPE
    SYNTAX --?? syntax is not convertable to SMIv1
           Counter
--  Units
--    Octets
    ACCESS read-only
    STATUS mandatory
    DESCRIPTION
        "This object indicates the number of egress
        octets whose COS value matched the value of the 
        cportQosCosValue object."
    ::= { cportQosCosStatsEntry 5 }

ciscoPortQosMIBGroup OBJECT IDENTIFIER ::= { ciscoPortQosMIBGroups 1 }
-- OBJECT-GROUP
--  Status
--    mandatory
--  Descr
--    A collection of objects providing Port QoS
--    features.
--  objects
--    cportQosRLConfigEnable, cportQosRLConfigRate, 
--    cportQosRLConfigBurstSize, cportQosTSConfigEnable, 
--    cportQosTSConfigRate, cportQosTSConfigBurstSize

ciscoPortQosStatsMIBGroup OBJECT IDENTIFIER ::= { ciscoPortQosMIBGroups 2 }
-- OBJECT-GROUP
--  Status
--    deprecated
--  Descr
--    A collection of objects providing per Port QoS
--    statistics.     
--    Replaced by: ciscoPortQosStatsMIBGroupRev1
--  objects
--    cportQosIndexType, cportQosPrePolicyPkts, 
--    cportQosPrePolicyOctets, cportQosPostPolicyOctets, 
--    cportQosPostPolicyPkts, cportQosDropPkts, cportQosDropOctets, 
--    cportQosClassifiedOctets, cportQosClassifiedPkts

ciscoPortQosStatsMIBGroupRev1 OBJECT IDENTIFIER ::= { ciscoPortQosMIBGroups 3 }
-- OBJECT-GROUP
--  Status
--    deprecated
--  Descr
--    A collection of objects providing per Port QoS
--    statistics.
--  objects
--    cportQosIndexType, cportQosPrePolicyPkts, 
--    cportQosPrePolicyOctets, cportQosPostPolicyOctets, 
--    cportQosPostPolicyPkts, cportQosDropPkts, cportQosDropOctets, 
--    cportQosClassifiedOctets, cportQosClassifiedPkts, 
--    cportQosNoChangePkts, cportQosNoChangeOctets

ciscoPortQosStatsMIBGroupRev2 OBJECT IDENTIFIER ::= { ciscoPortQosMIBGroups 4 }
-- OBJECT-GROUP
--  Status
--    mandatory
--  Descr
--    A collection of objects providing per Port QoS
--    statistics.
--  objects
--    cportQosIndexTypeNew, cportQosPrePolicyPkts, 
--    cportQosPrePolicyOctets, cportQosPostPolicyOctets, 
--    cportQosPostPolicyPkts, cportQosDropPkts, cportQosDropOctets, 
--    cportQosClassifiedOctets, cportQosClassifiedPkts, 
--    cportQosNoChangePkts, cportQosNoChangeOctets, 
--    cportQosInProfPolicyPkts, cportQosOutOfProfPolicyPkts

ciscoPortQosStatsMIBGroupRev2Supp1 OBJECT IDENTIFIER ::= { ciscoPortQosMIBGroups 5 }
-- OBJECT-GROUP
--  Status
--    mandatory
--  Descr
--    A collection of objects providing per Port QoS
--    statistics.
--  objects
--    cportQosVlanInProfPolicyPkts, cportQosVlanOutOfProfPolicyPkts

ciscoPortQosStatsMIBGroupRev2Supp2 OBJECT IDENTIFIER ::= { ciscoPortQosMIBGroups 6 }
-- OBJECT-GROUP
--  Status
--    mandatory
--  Descr
--    A collection of objects providing per Port QoS
--    statistics.
--  objects
--    cportQosInProfPolicyOctets, cportQosOutOfProfPolicyOctets, 
--    cportQosViolateProfPolicyPkts, 
--    cportQosViolateProfPolicyOctets

ciscoPortQosStatsMIBGroupRev2Supp3 OBJECT IDENTIFIER ::= { ciscoPortQosMIBGroups 7 }
-- OBJECT-GROUP
--  Status
--    mandatory
--  Descr
--    A collection of objects providing per Port QoS
--    statistics.
--  objects
--    cportQosVlanInProfPolicyOctets, 
--    cportQosVlanOutOfProfPolicyOctets, 
--    cportQosVlanViolateProfPolicyPkts, 
--    cportQosVlanViolateProfPolicyOctets

ciscoPortQosStatsMIBGroupRev2Supp4 OBJECT IDENTIFIER ::= { ciscoPortQosMIBGroups 8 }
-- OBJECT-GROUP
--  Status
--    mandatory
--  Descr
--    A collection of objects providing per Port QoS
--    statistics.
--  objects
--    cportQosQueueEnqueuePkts, cportQosQueueDropPkts

ciscoPortQosStatsMIBGroupRev2Supp5 OBJECT IDENTIFIER ::= { ciscoPortQosMIBGroups 9 }
-- OBJECT-GROUP
--  Status
--    mandatory
--  Descr
--    A collection of objects providing per Port QoS
--    statistics.
--  objects
--    cportQosClassName, cportQosClassEnqueuePkts, 
--    cportQosClassDropPkts, cportQosClassDiscontinuityTime

ciscoPortQosStatsMIBGroupRev2Supp6 OBJECT IDENTIFIER ::= { ciscoPortQosMIBGroups 10 }
-- OBJECT-GROUP
--  Status
--    mandatory
--  Descr
--    A collection of objects providing per Port QoS
--    statistics.
--  objects
--    cportQosClassNameLevel1, cportQosClassNameLevel2, 
--    cportQosPoliceConformPkts, cportQosPoliceConformOctets, 
--    cportQosPoliceExceedPkts, cportQosPoliceExceedOctets, 
--    cportQosPoliceViolatePkts, cportQosPoliceViolateOctets, 
--    cportQosPoliceConformRate, cportQosPoliceExceedRate, 
--    cportQosPoliceViolateRate, cportQosPoliceDiscontinuityTime

ciscoPortQosStatsMIBGroupRev2Supp7 OBJECT IDENTIFIER ::= { ciscoPortQosMIBGroups 11 }
-- OBJECT-GROUP
--  Status
--    mandatory
--  Descr
--    A collection of objects providing per Port QoS
--    statistics.
--  objects
--    cportQosDscpIngressPkts, cportQosDscpIngressOctets, 
--    cportQosDscpEgressPkts, cportQosDscpEgressOctets

ciscoPortQosStatsMIBGroupRev2Supp8 OBJECT IDENTIFIER ::= { ciscoPortQosMIBGroups 12 }
-- OBJECT-GROUP
--  Status
--    mandatory
--  Descr
--    A collection of objects providing per Port QoS
--    statistics.
--  objects
--    cportQosCosIngressPkts, cportQosCosIngressOctets, 
--    cportQosCosEgressPkts, cportQosCosEgressOctets

ciscoPortQosMIBCompliance OBJECT IDENTIFIER ::= { ciscoPortQosMIBCompliances 1 }
-- MODULE-COMPLIANCE
--  Status
--    deprecated
--  Descr
--    The compliance statement for entities which
--    implement Port QoS functions on a Cisco router.
--  Module
--    >>current<<
--   MandGroup
--    ciscoPortQosMIBGroup
--   OptGroup
--    ciscoPortQosStatsMIBGroup

ciscoPortQosMIBComplianceRev1 OBJECT IDENTIFIER ::= { ciscoPortQosMIBCompliances 2 }
-- MODULE-COMPLIANCE
--  Status
--    deprecated
--  Descr
--    The compliance statement for entities which
--    implement Port QoS functions on a Cisco router.
--  Module
--    >>current<<
--   MandGroup
--    ciscoPortQosMIBGroup
--   OptGroup
--    ciscoPortQosStatsMIBGroupRev1

ciscoPortQosMIBComplianceRev2 OBJECT IDENTIFIER ::= { ciscoPortQosMIBCompliances 3 }
-- MODULE-COMPLIANCE
--  Status
--    deprecated
--  Descr
--    The compliance statement for entities which
--    implement Port QoS functions on a Cisco router.
--  Module
--    >>current<<
--   MandGroup
--    ciscoPortQosMIBGroup
--   OptGroup
--    ciscoPortQosStatsMIBGroupRev2
--   ObjVar
--    cportQosIndexTypeNew

ciscoPortQosMIBComplianceRev3 OBJECT IDENTIFIER ::= { ciscoPortQosMIBCompliances 4 }
-- MODULE-COMPLIANCE
--  Status
--    deprecated
--  Descr
--    The compliance statement for entities which
--    implement Port QoS functions on a Cisco router.
--  Module
--    >>current<<
--   MandGroup
--    ciscoPortQosMIBGroup
--   OptGroup
--    ciscoPortQosStatsMIBGroupRev2
--   OptGroup
--    ciscoPortQosStatsMIBGroupRev2Supp1
--   ObjVar
--    cportQosIndexTypeNew

ciscoPortQosMIBComplianceRev4 OBJECT IDENTIFIER ::= { ciscoPortQosMIBCompliances 5 }
-- MODULE-COMPLIANCE
--  Status
--    deprecated
--  Descr
--    The compliance statement for entities which
--    implement Port QoS functions on a Cisco router.
--  Module
--    >>current<<
--   MandGroup
--    ciscoPortQosMIBGroup
--   OptGroup
--    ciscoPortQosStatsMIBGroupRev2
--   OptGroup
--    ciscoPortQosStatsMIBGroupRev2Supp1
--   OptGroup
--    ciscoPortQosStatsMIBGroupRev2Supp2
--   ObjVar
--    cportQosIndexTypeNew

ciscoPortQosMIBComplianceRev5 OBJECT IDENTIFIER ::= { ciscoPortQosMIBCompliances 6 }
-- MODULE-COMPLIANCE
--  Status
--    deprecated
--  Descr
--    The compliance statement for entities which
--    implement Port QoS functions on a Cisco router.
--  Module
--    >>current<<
--   MandGroup
--    ciscoPortQosMIBGroup
--   OptGroup
--    ciscoPortQosStatsMIBGroupRev2
--   OptGroup
--    ciscoPortQosStatsMIBGroupRev2Supp1
--   OptGroup
--    ciscoPortQosStatsMIBGroupRev2Supp2
--   OptGroup
--    ciscoPortQosStatsMIBGroupRev2Supp3
--   ObjVar
--    cportQosIndexTypeNew

ciscoPortQosMIBComplianceRev6 OBJECT IDENTIFIER ::= { ciscoPortQosMIBCompliances 7 }
-- MODULE-COMPLIANCE
--  Status
--    mandatory
--  Descr
--    The compliance statement for entities which
--    implement Port QoS functions on a Cisco router.
--  Module
--    >>current<<
--   MandGroup
--    ciscoPortQosMIBGroup
--   OptGroup
--    ciscoPortQosStatsMIBGroupRev2
--   OptGroup
--    ciscoPortQosStatsMIBGroupRev2Supp1
--   OptGroup
--    ciscoPortQosStatsMIBGroupRev2Supp2
--   OptGroup
--    ciscoPortQosStatsMIBGroupRev2Supp3
--   OptGroup
--    ciscoPortQosStatsMIBGroupRev2Supp4
--   OptGroup
--    ciscoPortQosStatsMIBGroupRev2Supp5
--   OptGroup
--    ciscoPortQosStatsMIBGroupRev2Supp6
--   OptGroup
--    ciscoPortQosStatsMIBGroupRev2Supp7
--   OptGroup
--    ciscoPortQosStatsMIBGroupRev2Supp8
--   ObjVar
--    cportQosIndexTypeNew


END
