-- MIB file created 05-Oct-2006 20:10:48, by
--   SMICng version 2.2.11-beta(PRO)(Solaris), January 20, 2001. Enterprise key cisco.com

CISCO-SANTAP-MIB DEFINITIONS ::= BEGIN

-- From file: "CISCO-SANTAP-MIB.my"
-- Compile options "4 7 F H N O W 03 06 0B 0G 0N 0T"

IMPORTS
    RowStatus, TruthValue
            FROM SNMPv2-TC-v1
    ciscoMgmt
            FROM CISCO-SMI
    PhysicalIndex
            FROM ENTITY-MIB
    vsanIndex
            FROM CISCO-VSAN-MIB
    SnmpAdminString
            FROM SNMP-FRAMEWORK-MIB
    InterfaceIndex
            FROM IF-MIB
    VsanIndex, FcNameIdOrZero, FcNameId
            FROM CISCO-ST-TC
    Gauge
            FROM RFC1155-SMI
    OBJECT-TYPE
            FROM RFC-1212;

ciscoSanTapMIB OBJECT IDENTIFIER ::= { ciscoMgmt 463 }
-- MODULE-IDENTITY
--  LastUpdated
--    200603160000Z
--  OrgName
--    Cisco Systems Inc.
--  ContactInfo
--         Cisco Systems
--          Customer Service
--    Postal: 170 W Tasman Drive
--          San Jose, CA  95134
--          USA
--    Tel: +1 800 553 -NETS
--    E-mail: cs-san@cisco.com
--  Descr
--    MIB module to provide information about the SanTap 
--     service configuration.             
--    
--     SanTap is a fibre channel switch based capability that 
--     provides a reliable copy of the data flowing between 
--     a set of one or more initiators and a set of one or 
--     more targets connected to the fabric.
--    
--     Adminstrator must configure the switch to create the 
--     Control Virtual Target (CVT) for the SanTap service. 
--     CVTs are used to implement the control path which process 
--     all SanTap service requests sent out by an appliance. 
--    
--     Prior to requesting for SanTap service the appliance 
--     contacts the CVT, specifies the initiator and the target 
--     for replicating the data flowing between them.
--          
--     This MIB provides an interface to configure the CVT for 
--     the SanTap service on the fibre channel switch modules.
--    
--     Glossary of terms used in this MIB:
--    
--     Fabric - The set of physically connected fibre channel
--              switches.
--    
--     VSAN - Virtual Storage Area Network, similar to a 
--            Virtual Fabric as defined by T11. 
--    
--     WWN  - World Wide Name. Mechanism of uniquely 
--            identifying the devices in Fibre Channel 
--            Networks. 
--    
--     Appliance - It is a storage target, which can  
--            requests the SanTap service for the reliable 
--            copy of the data flowing between a specific 
--            host initiator and a target. 
--    
--     CVT  - Control Virtual Target. It is a logical target 
--            port that resides on the switch and is used 
--            for the purpose of communicating control traffic 
--            from an appliance.
--    
--     DVT  - Data Virtual Target.  It is a logical target port
--            that resides on the switch and is used to intercept 
--            traffic meant for a real target.
--  RevDate
--    200603160000Z
--  RevDescr
--    Added 'cstDVTLunSizeHandling' and 'cstDVTIOTimeout' 
--     columnar objects to 'cstDVTConfigTable'.
--  RevDate
--    200510270000Z
--  RevDescr
--    Added the 'cstDVTConfigTable'.  Added 'cstCVTName' 
--     columnar object to 'cstServiceConfigTable'.
--  RevDate
--    200502020000Z
--  RevDescr
--    Initial version of this MIB.

ciscoSanTapMIBObjects OBJECT IDENTIFIER ::= { ciscoSanTapMIB 1 }
ciscoSanTapMIBConformance OBJECT IDENTIFIER ::= { ciscoSanTapMIB 2 }
ciscoSanTapNotifications OBJECT IDENTIFIER ::= { ciscoSanTapMIB 3 }
ciscoSanTapMIBCompliances OBJECT IDENTIFIER ::= { ciscoSanTapMIBConformance 1 }
ciscoSanTapMIBGroups OBJECT IDENTIFIER ::= { ciscoSanTapMIBConformance 2 }

cstModuleTable OBJECT-TYPE
    SYNTAX SEQUENCE OF CstModuleEntry
    ACCESS not-accessible
    STATUS mandatory
    DESCRIPTION
        "A table listing the modules on which SanTap service can 
         be configured and CVT can be created by the user.
        
         The entry in the cstServiceConfigTable can only be 
         created on a module present in the cstModuleTable."
    ::= { ciscoSanTapMIBObjects 1 }

cstModuleEntry OBJECT-TYPE
    SYNTAX CstModuleEntry
    ACCESS not-accessible
    STATUS mandatory
    DESCRIPTION
        "An entry in this table.
         The cstModuleId denotes the entPhysicalIndex of the
         module on which SanTap service can be configured."
    INDEX { cstModuleId }
    ::= { cstModuleTable 1 }

CstModuleEntry ::= SEQUENCE {
    cstModuleId PhysicalIndex
    }

cstModuleId OBJECT-TYPE
    SYNTAX PhysicalIndex
--    Rsyntax INTEGER(1..2147483647)
    ACCESS read-only
    STATUS mandatory
    DESCRIPTION
        "This object specifies the physical index of the entity  
         with entPhysicalClass as 'module' on which SanTap service 
         can be configured by the user.
         This is same as the entPhysicalIndex of the module."
    ::= { cstModuleEntry 1 }

cstServiceConfigTable OBJECT-TYPE
    SYNTAX SEQUENCE OF CstServiceConfigEntry
    ACCESS not-accessible
    STATUS mandatory
    DESCRIPTION
        "This table provides information about the list of 
         all CVTs created and configured in the system. 
        
         A new entry creation in this table, creates a CVT on the 
         module specified by the corresponding instance index 
         'cstModuleId' and configures the CVT on the VSAN 
         specified by the corresponding instance index 'vsanIndex'.
        
         A row creation in this table, with an existing 
         module physical index  but different 'vsanIndex' 
         configures the already created CVT on the module into
         VSAN specified by the 'vsanIndex'.
        
         Deleting an entry from this table, unconfigures the
         CVT created on the module specified by the corresponding 
         instance index 'cstModuleId' on the VSAN represented 
         by the corresponding instance index 'vsanIndex'. If there 
         are no more entries in this table for this module then
         the CVT will be deleted from the corresponding module.
        
         For example, If there is no entry in this table for a
         module pysical Index '22', then a new entry creation 
         with cstModuleId '22' vsanIndex 'n1' creates a
         CVT on this module and configures the CVT on VSAN 'n1'.
         And a new row is created in this table.
        
         Any subsequent entry creation with cstModuleId '22'
         vsanIndex 'n2' only configures the previously created 
         CVT on vsan 'n2' and a new row is created in this table.
        
         Similarly for any delete request with cstModuleId '22'
         vsanIndex 'n1'/'n2' unconfigures the CVT created on the 
         vsan 'n1'/'n2' and the corresponding row is deleted from 
         the table. 
        
         If there is only one entry with cstModuleId '22' 
         and vsan 'n' exists in the table, then any delete request  
         with cstModuleId '22' vsan 'n' unconfigures the CVT on 
         vsan 'n' and deletes the CVT. The corresponding row is 
         deleted from the table."
    ::= { ciscoSanTapMIBObjects 2 }

cstServiceConfigEntry OBJECT-TYPE
    SYNTAX CstServiceConfigEntry
    ACCESS not-accessible
    STATUS mandatory
    DESCRIPTION
        "An entry containing information about a CVT configuration
         for the SanTap service.
        
         The 'cstModuleId' denotes the module on which the user 
         wants the SanTap service to be configured and the CVT to be
         created.  
        
         The index 'vsanIndex' represents the VSAN on which the
         CVT needs to be configured. It represents the VSAN on 
         which CVT and the appliance communicate to establish the 
         control path for processing the SanTap service requests."
    INDEX { cstModuleId, vsanIndex }
    ::= { cstServiceConfigTable 1 }

CstServiceConfigEntry ::= SEQUENCE {
    cstCVTNodeWwn FcNameIdOrZero,
    cstCVTPortWwn FcNameIdOrZero,
    cstServiceConfigRowStatus RowStatus,
    cstCVTName SnmpAdminString
    }

cstCVTNodeWwn OBJECT-TYPE
    SYNTAX FcNameIdOrZero
--    Rsyntax OCTET STRING(SIZE(0|8|16))
    ACCESS read-only
    STATUS mandatory
    DESCRIPTION
        "This object represents the Node World-Wide Name of the 
         CVT created on the module represented by the corresponding 
         entity index 'cstModuleId'."
    ::= { cstServiceConfigEntry 1 }

cstCVTPortWwn OBJECT-TYPE
    SYNTAX FcNameIdOrZero
--    Rsyntax OCTET STRING(SIZE(0|8|16))
    ACCESS read-only
    STATUS mandatory
    DESCRIPTION
        "This object represents the Port World-Wide Name of the 
         CVT created on the module represented by the corresponding 
         entity index 'cstModuleId'."
    ::= { cstServiceConfigEntry 2 }

cstServiceConfigRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row."
    ::= { cstServiceConfigEntry 3 }

cstCVTName OBJECT-TYPE
    SYNTAX SnmpAdminString(SIZE(0..255))
--    Rsyntax OCTET STRING(SIZE(0..255))
    ACCESS read-write
    STATUS mandatory
    DESCRIPTION
        "The administratively assigned name for this CVT."
    DEFVAL { "" }
    ::= { cstServiceConfigEntry 4 }

cstDVTConfigTable OBJECT-TYPE
    SYNTAX SEQUENCE OF CstDVTConfigEntry
    ACCESS not-accessible
    STATUS mandatory
    DESCRIPTION
        "This table provides information about the list of 
         all DVTs created and configured in the system.
        
         A new entry creation in this table, creates a DVT 
         corresponding to the target PWWN 'cstDVTPortWwn' on
         the VSAN 'vsanIndex'.
        
         Deleting an entry from this table, unconfigures the
         DVT corresponding to 'cstDVTPortWwn' from the VSAN
         'vsanIndex'.
        
         The index 'vsanIndex' represents the VSAN on which the
         DVT needs to be created.  The index 'vsanIndex' should 
         be a known VSAN on the switch. 
        
         The index 'cstDVTPortWWN' represents the Port WWN of the 
         real target for which a corresponding DVT is to be created.
         The DVT will have the same Port WWN as the target. The
         index 'cstDVTPortWWN' should correspond to a known target 
         on the switch.  
        
         By default no entries exist in the table."
    ::= { ciscoSanTapMIBObjects 3 }

cstDVTConfigEntry OBJECT-TYPE
    SYNTAX CstDVTConfigEntry
    ACCESS not-accessible
    STATUS mandatory
    DESCRIPTION
        "An entry containing information about a DVT configuration
         for the SanTap service."
    INDEX { vsanIndex, cstDVTPortWwn }
    ::= { cstDVTConfigTable 1 }

CstDVTConfigEntry ::= SEQUENCE {
    cstDVTPortWwn FcNameId,
    cstDVTTargetVsan VsanIndex,
    cstDVTPort InterfaceIndex,
    cstDVTName SnmpAdminString,
    cstDVTRowStatus RowStatus,
    cstDVTLunSizeHandling TruthValue,
    cstDVTIOTimeout Gauge
    }

cstDVTPortWwn OBJECT-TYPE
    SYNTAX FcNameId
--    Rsyntax OCTET STRING(SIZE(8))
    ACCESS not-accessible
    STATUS mandatory
    DESCRIPTION
        "This object represents the port world-wide name of the 
         created DVT.  It will be the same as the port world-wide
         name of the real target for which data is to be replicated."
    ::= { cstDVTConfigEntry 1 }

cstDVTTargetVsan OBJECT-TYPE
    SYNTAX VsanIndex
--    Rsyntax INTEGER(1..4094)
    ACCESS read-write
    STATUS mandatory
    DESCRIPTION
        "This object represents the VSAN of the real target for
         which this DVT is being created.
        
         This object MUST be set to a valid value concurrently 
         with setting the corresponding instance of cstDVTRowStatus
         to 'active'. This object cannot be modified while the value
         of the corresponding instance of cstDVTRowStatus is 
         'active'."
    ::= { cstDVTConfigEntry 2 }

cstDVTPort OBJECT-TYPE
    SYNTAX InterfaceIndex
--    Rsyntax INTEGER(1..2147483647)
    ACCESS read-write
    STATUS mandatory
    DESCRIPTION
        "This object represents the port on the module where the
         DVT will be created.
        
         This object MUST be set to a valid value concurrently 
         with setting the corresponding instance of cstDVTRowStatus
         to 'active'. This object cannot be modified while the value
         of the corresponding instance of cstDVTRowStatus is 
         'active'."
    ::= { cstDVTConfigEntry 3 }

cstDVTName OBJECT-TYPE
    SYNTAX SnmpAdminString(SIZE(0..255))
--    Rsyntax OCTET STRING(SIZE(0..255))
    ACCESS read-write
    STATUS mandatory
    DESCRIPTION
        "The administratively assigned name for this DVT."
    DEFVAL { "" }
    ::= { cstDVTConfigEntry 4 }

cstDVTRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row."
    ::= { cstDVTConfigEntry 5 }

cstDVTLunSizeHandling OBJECT-TYPE
    SYNTAX TruthValue
--    Rsyntax INTEGER {
--        true(1),
--        false(2)
--        }
    ACCESS read-write
    STATUS mandatory
    DESCRIPTION
        "This object indicates if the DVT should use the 
         real target LUN size for the virtual LUN or the 
         max LUN size supported which is 2TB.
        
         A value of false for this object indicates the 
         real target LUN size should be used. This object
         should be set during the DVT creation time and
         cannot be modified later."
    DEFVAL { true }
    ::= { cstDVTConfigEntry 6 }

cstDVTIOTimeout OBJECT-TYPE
    SYNTAX Gauge(10..200)
--  Units
--    seconds
    ACCESS read-write
    STATUS mandatory
    DESCRIPTION
        "This object represents the IO timeout value 
         associated with the DVT. This object should 
         be set during the DVT creation time and cannot 
         be modified later."
    DEFVAL { 10 }
    ::= { cstDVTConfigEntry 7 }

ciscoSanTapServiceConfigGroup OBJECT IDENTIFIER ::= { ciscoSanTapMIBGroups 1 }
-- OBJECT-GROUP
--  Status
--    deprecated
--  Descr
--    A Collection of objects to configure the CVT for SanTap
--     service.
--  objects
--    cstModuleId, cstCVTNodeWwn, cstCVTPortWwn, 
--    cstServiceConfigRowStatus

ciscoSanTapServiceConfigGroupRev1 OBJECT IDENTIFIER ::= { ciscoSanTapMIBGroups 2 }
-- OBJECT-GROUP
--  Status
--    mandatory
--  Descr
--    A Collection of objects to configure the CVT for SanTap
--     service.
--  objects
--    cstModuleId, cstCVTNodeWwn, cstCVTPortWwn, 
--    cstServiceConfigRowStatus, cstCVTName

ciscoSanTapDVTConfigGroup OBJECT IDENTIFIER ::= { ciscoSanTapMIBGroups 3 }
-- OBJECT-GROUP
--  Status
--    deprecated
--  Descr
--    A Collection of objects to configure the DVT for SanTap
--     service.
--  objects
--    cstDVTTargetVsan, cstDVTPort, cstDVTName, cstDVTRowStatus

ciscoSanTapDVTConfigGroup1 OBJECT IDENTIFIER ::= { ciscoSanTapMIBGroups 4 }
-- OBJECT-GROUP
--  Status
--    mandatory
--  Descr
--    A Collection of objects to configure the DVT for SanTap
--     service.
--  objects
--    cstDVTTargetVsan, cstDVTPort, cstDVTName, cstDVTRowStatus, 
--    cstDVTLunSizeHandling, cstDVTIOTimeout

ciscoSanTapMIBCompliance OBJECT IDENTIFIER ::= { ciscoSanTapMIBCompliances 1 }
-- MODULE-COMPLIANCE
--  Status
--    deprecated
--  Descr
--    Compliance statement for entites which implement 
--     the CISCO SANTAP MIB.
--  Module
--    >>current<<
--   MandGroup
--    ciscoSanTapServiceConfigGroup
--   ObjVar
--    cstServiceConfigRowStatus

ciscoSanTapMIBComplianceRev1 OBJECT IDENTIFIER ::= { ciscoSanTapMIBCompliances 2 }
-- MODULE-COMPLIANCE
--  Status
--    deprecated
--  Descr
--    Compliance statement for entites which implement 
--     the CISCO SANTAP MIB.
--  Module
--    >>current<<
--   MandGroup
--    ciscoSanTapServiceConfigGroupRev1
--   MandGroup
--    ciscoSanTapDVTConfigGroup
--   ObjVar
--    cstServiceConfigRowStatus
--   ObjVar
--    cstDVTRowStatus

ciscoSanTapMIBComplianceRev2 OBJECT IDENTIFIER ::= { ciscoSanTapMIBCompliances 3 }
-- MODULE-COMPLIANCE
--  Status
--    mandatory
--  Descr
--    Compliance statement for entites which implement 
--     the CISCO SANTAP MIB.
--  Module
--    >>current<<
--   MandGroup
--    ciscoSanTapServiceConfigGroupRev1
--   MandGroup
--    ciscoSanTapDVTConfigGroup1
--   ObjVar
--    cstServiceConfigRowStatus
--   ObjVar
--    cstDVTRowStatus


END
