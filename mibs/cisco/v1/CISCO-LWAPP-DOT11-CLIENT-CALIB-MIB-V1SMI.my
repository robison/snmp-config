-- MIB file created 20-Jun-2007 17:13:15, by
--   SMICng version 2.2.11-beta(PRO)(Solaris), January 20, 2001. Enterprise key cisco.com

CISCO-LWAPP-DOT11-CLIENT-CALIB-MIB DEFINITIONS ::= BEGIN

-- From file: "CISCO-LWAPP-DOT11-CLIENT-CALIB-MIB.my"
-- Compile options "4 7 F H N O W 03 06 0B 0G 0N 0T"

IMPORTS
    MacAddress, TimeInterval, RowStatus
            FROM SNMPv2-TC-v1
    ciscoMgmt
            FROM CISCO-SMI
    Gauge
            FROM RFC1155-SMI
    OBJECT-TYPE
            FROM RFC-1212;

ciscoLwappDot11ClientCalibMIB OBJECT IDENTIFIER ::= { ciscoMgmt 522 }
-- MODULE-IDENTITY
--  LastUpdated
--    200604110000Z
--  OrgName
--    Cisco Systems Inc.
--  ContactInfo
--            Cisco Systems,
--             Customer Service
--     Postal: 170 West Tasman Drive
--             San Jose, CA  95134
--             USA
--        Tel: +1 800 553-NETS
--    
--      Email: cs-wnbu-snmp@cisco.com
--  Descr
--    This MIB is intended to be implemented on all those
--    devices operating as Central controllers, that
--    terminate the Light Weight Access Point Protocol
--    tunnel from Cisco Light-weight LWAPP Access Points.
--    
--    Information provided by this MIB is about the
--    configuration and monitoring of 802.11 wireless
--    clients in the network.
--    
--    The relationship between CC and the LWAPP APs
--    can be depicted as follows:
--    
--    +......+     +......+     +......+           +......+
--    +      +     +      +     +      +           +      +
--    +  CC  +     +  CC  +     +  CC  +           +  CC  +
--    +      +     +      +     +      +           +      +
--    +......+     +......+     +......+           +......+
--    ..            .             .                 .
--    ..            .             .                 .
--    .  .            .             .                 .
--    .    .            .             .                 .
--    .      .            .             .                 .
--    .        .            .             .                 .
--    +......+ +......+     +......+      +......+          +......+
--    +      + +      +     +      +      +      +          +      +
--    +  AP  + +  AP  +     +  AP  +      +  AP  +          +  AP  +
--    +      + +      +     +      +      +      +          +      +
--    +......+ +......+     +......+      +......+          +......+
--    .              .             .                 .
--    .  .              .             .                 .
--    .    .              .             .                 .
--    .      .              .             .                 .
--    .        .              .             .                 .
--    +......+ +......+     +......+      +......+          +......+
--    +      + +      +     +      +      +      +          +      +
--    +  MN  + +  MN  +     +  MN  +      +  MN  +          +  MN  +
--    +      + +      +     +      +      +      +          +      +
--    +......+ +......+     +......+      +......+          +......+
--    
--    The LWAPP tunnel exists between the controller and
--    the APs.  The MNs communicate with the APs through
--    the protocol defined by the 802.11 standard.
--    
--    LWAPP APs, upon bootup, discover and join one of the
--    controllers and the controller pushes the configuration,
--    that includes the WLAN parameters, to the LWAPP APs.
--    The APs then encapsulate all the 802.11 frames from
--    wireless clients inside LWAPP frames and forward
--    the LWAPP frames to the controller.
--    
--                       GLOSSARY
--    
--    Access Point ( AP )
--    
--    An entity that contains an 802.11 medium access
--    control ( MAC ) and physical layer ( PHY ) interface
--    and provides access to the distribution services via
--    the wireless medium for associated clients.  
--    
--    LWAPP APs encapsulate all the 802.11 frames in
--    LWAPP frames and sends them to the controller to which
--    it is logically connected.
--    
--    Light Weight Access Point Protocol ( LWAPP ) 
--    
--    This is a generic protocol that defines the 
--    communication between the Access Points and the
--    Central Controller.
--    
--    Mobile Node ( MN )
--    
--    A roaming 802.11 wireless device in a wireless
--    network associated with an access point. Mobile Node,
--    Mobile Station(Ms) and client are used 
--    interchangeably. 
--    
--    REFERENCE
--    
--    [1] Wireless LAN Medium Access Control ( MAC ) and
--    Physical Layer ( PHY ) Specifications 
--    
--    [2] Draft-obara-capwap-lwapp-00.txt, IETF Light 
--    Weight Access Point Protocol 
--  RevDate
--    200604110000Z
--  RevDescr
--    Initial version of this MIB module. 

ciscoLwappDot11ClientCalibMIBNotifs OBJECT IDENTIFIER ::= { ciscoLwappDot11ClientCalibMIB 0 }
ciscoLwappDot11ClientCalibMIBObjects OBJECT IDENTIFIER ::= { ciscoLwappDot11ClientCalibMIB 1 }
ciscoLwappDot11ClientCalibMIBConform OBJECT IDENTIFIER ::= { ciscoLwappDot11ClientCalibMIB 2 }
cldccConfig     OBJECT IDENTIFIER ::= { ciscoLwappDot11ClientCalibMIBObjects 1 }
ciscoLwappDot11ClientCalibMIBCompliances OBJECT IDENTIFIER ::= { ciscoLwappDot11ClientCalibMIBConform 1 }
ciscoLwappDot11ClientCalibMIBGroups OBJECT IDENTIFIER ::= { ciscoLwappDot11ClientCalibMIBConform 2 }

cLD11ClientCalibTable OBJECT-TYPE
    SYNTAX SEQUENCE OF CLD11ClientCalibEntry
    ACCESS not-accessible
    STATUS mandatory
    DESCRIPTION
        "This table represents the calibration for the
        802.11 wireless clients that would associate
        to the APs that have joined this controller.
        
        An entry is created through an explicit management
        action initiated by the administrator through a
        network management station by specifying the
        calibration parameters for a particular client
        identified by cLD11ClientCalibMacAddress and setting
        the RowStatus object to 'createAndGo'.  An existing
        entry is deleted by setting the RowStatus object to 
        'destroy'.  The object cLD11ClientCalibTableMaxEntries
        represents the maximum number of entries in this
        table. "
    ::= { cldccConfig 1 }

cLD11ClientCalibEntry OBJECT-TYPE
    SYNTAX CLD11ClientCalibEntry
    ACCESS not-accessible
    STATUS mandatory
    DESCRIPTION
        "Each entry represents a conceptual row in this
        table and provides the information about the
        calibration parameters for wireless clients. "
    INDEX { cLD11ClientCalibMacAddress }
    ::= { cLD11ClientCalibTable 1 }

CLD11ClientCalibEntry ::= SEQUENCE {
    cLD11ClientCalibMacAddress MacAddress,
    cLD11ClientCalibBeaconInterval TimeInterval,
    cLD11ClientCalibRowStatus RowStatus
    }

cLD11ClientCalibMacAddress OBJECT-TYPE
    SYNTAX MacAddress
--    Rsyntax OCTET STRING(SIZE(6))
    ACCESS not-accessible
    STATUS mandatory
    DESCRIPTION
        "This object specifies the MAC address of the
        802.11 wireless client for which the 
        calibration parameters in this entry are 
        applicable and uniquely identifies this entry. "
    ::= { cLD11ClientCalibEntry 1 }

cLD11ClientCalibBeaconInterval OBJECT-TYPE
    SYNTAX TimeInterval(400..3240000)
--    Rsyntax INTEGER(400..3240000)
--  Units
--    hundredths-seconds
    ACCESS read-write
    STATUS mandatory
    DESCRIPTION
        "This object specifies the time interval, expressed
        here in hundredths of a second at which an AP
        issues radio measurement request messages to a
        client for every SSID.  It is not recommended to
        configure values less than 10 seconds (1000).
        The value configured through this object is
        reflected in the operation of the LWAPP APs only if
        cLD11ClientCalibBeaconEnabled is set to 'true'. "
    DEFVAL { 60000 }
    ::= { cLD11ClientCalibEntry 2 }

cLD11ClientCalibRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object that represents the status of a
        specific instance of a row in this table.
        Initially set to a value of 'createAndGo' by
        the User when a row is created, the status
        as represented by this object is automatically
        set to 'active' if and when the row creation
        is successful.  To delete the specific instance
        of a row, User should set this object to
        'destroy'. "
    ::= { cLD11ClientCalibEntry 3 }

cLD11ClientCalibTableMaxEntries OBJECT-TYPE
    SYNTAX Gauge(1..25)
    ACCESS read-write
    STATUS mandatory
    DESCRIPTION
        "This object represents the upper limit on the
        number of entries in cLD11ClientCalibTable. "
    DEFVAL { 5 }
    ::= { cldccConfig 2 }

ciscoLwappDot11ClientCalibMIBConfigGroup OBJECT IDENTIFIER ::= { ciscoLwappDot11ClientCalibMIBGroups 1 }
-- OBJECT-GROUP
--  Status
--    mandatory
--  Descr
--    This collection of objects specifies the required
--    calibration parameters for the 802.11 wireless 
--    clients. 
--  objects
--    cLD11ClientCalibBeaconInterval, cLD11ClientCalibRowStatus, 
--    cLD11ClientCalibTableMaxEntries

ciscoLwappDot11ClientCalibMIBCompliance OBJECT IDENTIFIER ::= { ciscoLwappDot11ClientCalibMIBCompliances 1 }
-- MODULE-COMPLIANCE
--  Status
--    mandatory
--  Descr
--    The compliance statement for the SNMP entities that
--    implement this MIB. 
--  Module
--    >>current<<
--   MandGroup
--    ciscoLwappDot11ClientCalibMIBConfigGroup


END
