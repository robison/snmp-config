-- MIB file created 28-Apr-2013 11:53:13, by
--   SMICng version 2.2.11-beta(PRO)(Solaris), January 20, 2001. Enterprise key cisco.com

CISCO-ERR-DISABLE-MIB DEFINITIONS ::= BEGIN

-- From file: "CISCO-ERR-DISABLE-MIB.my"
-- Compile options "4 7 F H N W 03 06 0B 0G 0N 0T"

IMPORTS
    ifIndex
            FROM IF-MIB
    TruthValue
            FROM SNMPv2-TC-v1
    TimeIntervalSec
            FROM CISCO-TC
    VlanIndexOrZero
            FROM CISCO-PRIVATE-VLAN-MIB
    ciscoMgmt
            FROM CISCO-SMI
    Gauge
            FROM RFC1155-SMI
    OBJECT-TYPE
            FROM RFC-1212
    TRAP-TYPE
            FROM RFC-1215;

ciscoErrDisableMIB OBJECT IDENTIFIER ::= { ciscoMgmt 548 }
-- MODULE-IDENTITY
--  LastUpdated
--    201304230000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-lan-switch-snmp@cisco.com
--  Descr
--    This MIB module provides the ability for a Network
--    Management Station (NMS) to configure and monitor the
--    error-disable feature via SNMP.
--    
--    The error-disable feature allows other software
--    features running in a system to operationally disable a
--    system entity upon detecting abnormal conditions. 
--    
--    Examples of such a system entity include interfaces, a
--    vlan configured in the system, or a VLAN allowed on
--    specific layer 2 multi-vlan interface.
--    
--    More specific examples:
--    
--        a) When BPDU guard is enabled on an interface
--        it is expected that no BPDU packets are received by
--        the interface. If a BPDU packet is received, then the
--        BPDU guard will operationally disable the
--        interface. 
--    
--        b) Users can configure a particular threshold of
--        broadcast packets received on an interface. If the
--        number of packets received exceeds the threshold, then
--        storm-control will disable the interface. 
--    
--        c) When unidirectional Link Detection (UDLD) detects a
--        unidirectional link on an interface, it can disable
--        the interface.
--    
--        d) On a trunk or a multi-vlan layer 2 port, if
--        port-security detects violation on a particular vlan,
--        then it can operationally disable that vlan on that
--        port.
--    
--    The definition of 'abnormal condition' is under the
--    control of features that make use of the error-disable
--    feature to disable system entities.
--    
--    The error-disable feature supports the following
--    configuration:
--    
--        1) Whether software features can in fact use the
--        error-disable feature upon detecting abnormal
--        conditions.
--           NOTE: Some software features will ALWAYS use the
--           error-disable feature to disable entities upon
--           detection of error.
--    
--        2) Whether the system can attempt to automatically
--        recover after a system entity has been disabled (e.g., 
--        A system can attempt to bring up a physical interface
--        which had been disabled earlier)
--    
--        3) If error recovery is possible, then the time
--        interval to wait before the system starts the recovery
--        attempt.
--  RevDate
--    201304230000Z
--  RevDescr
--    Added ciscoErrDisableFeatureFlapGroup and
--    a new enumeration flapControl(4) in 
--    cErrDisableFeatureConfigurable.
--  RevDate
--    201010190000Z
--  RevDescr
--    Added a new enumeration in CErrDisableFeatureID:
--    tranceiverIncomp(35).
--  RevDate
--    200903230000Z
--  RevDescr
--    Added the following new enumerations in
--    CErrDisableFeatureID:
--    sfpConfigMismatch(24), communityLimit(25), invalidPolicy(26),
--    lsGroup(27), ekey(28), portModeFailure(29), 
--    pppoeIaRateLimit(30), oamRemoteCriticalEvent(31),
--    oamRemoteDyingGasp(32), oamRemoteLinkFault(33),
--    and mvrp(34). 
--    
--    Added the new enumeration detectShutdownVlan(3) 
--    to cErrDisableFeatureConfigurable.
--    
--    Added ciscoErrDisableShutdownVlanGroup.
--  RevDate
--    200804070000Z
--  RevDescr
--    Added the following new enumerations in
--    CErrDisableFeatureID:
--    packetBuffer(18), macLimit(19), linkMonitorFailure(20),
--    oamRemoteFailure(21), dot1adIncompEtype(22), and
--    dot1adIncompTunnel(23).
--    
--    cErrDisableInterfaceEvent notification is deprecated 
--    and replaced by a new notification 
--    cErrDisableInterfaceEventRev1.
--    
--    Modified the description of cErrDisableNotifEnable
--    to add control for cErrDisableInterfaceEventRev1
--    notification.
--  RevDate
--    200605310000Z
--  RevDescr
--    Initial version of this MIB module.

ciscoErrDisableMIBNotifs OBJECT IDENTIFIER ::= { ciscoErrDisableMIB 0 }
ciscoErrDisableMIBObjects OBJECT IDENTIFIER ::= { ciscoErrDisableMIB 1 }
ciscoErrDisableMIBConform OBJECT IDENTIFIER ::= { ciscoErrDisableMIB 2 }
cErrDisableGlobalObjects OBJECT IDENTIFIER ::= { ciscoErrDisableMIBObjects 1 }
cErrDisableFeatureObjects OBJECT IDENTIFIER ::= { ciscoErrDisableMIBObjects 2 }
cErrDisableIfObjects OBJECT IDENTIFIER ::= { ciscoErrDisableMIBObjects 3 }
cErrDisableNotificationsPrefix OBJECT IDENTIFIER ::= { ciscoErrDisableMIBNotifs 1 }
ciscoErrDisableMIBCompliances OBJECT IDENTIFIER ::= { ciscoErrDisableMIBConform 1 }
ciscoErrDisableMIBGroups OBJECT IDENTIFIER ::= { ciscoErrDisableMIBConform 2 }

CErrDisableFeatureID ::= INTEGER {
        udld(1),
        bpduGuard(2),
        channelMisconfig(3),
        pagpFlap(4),
        dtpFlap(5),
        linkFlap(6),
        l2ptGuard(7),
        dot1xSecurityViolation(8),
        portSecurityViolation(9),
        gbicInvalid(10),
        dhcpRateLimit(11),
        unicastFlood(12),
        vmps(13),
        stormControl(14),
        inlinePower(15),
        arpInspection(16),
        portLoopback(17),
        packetBuffer(18),
        macLimit(19),
        linkMonitorFailure(20),
        oamRemoteFailure(21),
        dot1adIncompEtype(22),
        dot1adIncompTunnel(23),
        sfpConfigMismatch(24),
        communityLimit(25),
        invalidPolicy(26),
        lsGroup(27),
        ekey(28),
        portModeFailure(29),
        pppoeIaRateLimit(30),
        oamRemoteCriticalEvent(31),
        oamRemoteDyingGasp(32),
        oamRemoteLinkFault(33),
        mvrp(34),
        tranceiverIncomp(35)
        }
-- TEXTUAL-CONVENTION
--  Status
--    mandatory
--  Descr
--    An integer-value assigned to various features/events
--    that can error disable a system entity
--    
--    udld: Unidirectional Link Detection
--    
--    bpduGuard: Spanning Tree BPDU Guard feature that prevents
--    processing BPDU packets on an access interface
--    
--    channelMisconfig: General Link Aggregation mis-configuration
--    
--    pagpFlap: Cisco's PAGP Link Aggregation protocol errors
--    
--    dtpFlap: Dynamic Trunking Protocol errors
--    
--    linkFlap: Link State flapping
--    
--    l2ptGuard: L2 Protocol Tunnel errors
--    
--    dot1xSecurityViolation: 802.1x authentication violations
--    
--    portSecurity: Port Security violations
--    
--    gbicInvalid: Invalid GBIC errors (examples include
--    unsupported GBIC being inserted)
--    
--    dhcpRateLimit: DHCP snooping rate limit violation
--    
--    unicastFlood: Unicast Flooding threshold violations
--    
--    vmps: VLAN Membership Policy Server feature related errors
--    
--    stormControl: storm control (broadcast/multicast/unicast)
--    threshold violations
--    
--    inlinePower: Errors in inline power
--    
--    arpInspection: Errors detected by Dynamic Arp Inspection
--    (DAI) feature
--    
--    portLoopback: Interface Loopback Error
--    
--    packetBuffer: Packet Buffer Error
--    
--    macLimit: Errors detected by Mac Address Limit feature
--    
--    linkMonitorFailure: Link Monitoring failure
--    
--    oamRemoteFailure: Remote Failure detected by Ethernet OAM
--    (Operations, Administration, and Maintenance) feature   
--    
--    dot1adIncompEtype: 802.1ad Ether-type Incompatible errors
--    
--    dot1adIncompTunnel: 802.1ad Pdu Tunnel Incompatible errors
--    
--    sfpConfigMismatch: Mismatch on SFP configuration
--    
--    communityLimit: Vlan Community Limit violations
--    
--    invalidPolicy: QoS Policy violation
--    
--    lsGroup: Errors detected by Link State Group Tracking feature
--    
--    ekey: Errors detected by Error Key Mechanism
--    
--    portModeFailure: Port mode change failure
--    
--    pppoeIaRateLimit: Errors detected by PPPoE Intermediate Agent 
--    Rate Limit feature
--    
--    oamRemoteCriticalEvent: Ethernet OAM Remote Critical Event 
--    Failure  
--    
--    oamRemoteDyingGasp: Ethernet OAM Remote Dying Gasp Failure
--    
--    oamRemoteLinkFault: Ethernet OAM Remote Link Fault Failure
--    
--    mvrp: Errors detected by Multiple VLAN Registration Protocol
--    
--    tranceiverIncomp: Tranceiver incompatible errors

cErrDisableRecoveryInterval OBJECT-TYPE
    SYNTAX TimeIntervalSec
--    Rsyntax Gauge
    ACCESS read-write
    STATUS mandatory
    DESCRIPTION
        "This object specifies the error-disable recovery time
        interval.
        When a system entity is operationally disabled upon
        detecting abnormal condition by a particular feature,
        the system waits for a period equal to this time interval,
        and then re-enable the entity if automatic recovery is
        enabled for the feature."
    ::= { cErrDisableGlobalObjects 1 }

cErrDisableNotifEnable OBJECT-TYPE
    SYNTAX TruthValue
--    Rsyntax INTEGER {
--        true(1),
--        false(2)
--        }
    ACCESS read-write
    STATUS mandatory
    DESCRIPTION
        "This object specifies whether cErrDisableInterfaceEvent
        and cErrDisableInterfaceEventRev1
        notifications should be generated when a system entity is
        error-disabled."
    ::= { cErrDisableGlobalObjects 2 }

cErrDisableNotifRate OBJECT-TYPE
    SYNTAX Gauge
--  Units
--    Notification/Minute
    ACCESS read-write
    STATUS mandatory
    DESCRIPTION
        "The value of this object specifies the maximum number of
        error-disable notifications the device will generate per
        minute. 
        
        A value of '0' specifies no limit and the device
        will generate a notification for each error-disable
        event."
    ::= { cErrDisableGlobalObjects 3 }

cErrDisableFeatureTable OBJECT-TYPE
    SYNTAX SEQUENCE OF CErrDisableFeatureEntry
    ACCESS not-accessible
    STATUS mandatory
    DESCRIPTION
        "This table contains the error-disable related info
        for each feature employing the error-disable
        feature."
    ::= { cErrDisableFeatureObjects 1 }

cErrDisableFeatureEntry OBJECT-TYPE
    SYNTAX CErrDisableFeatureEntry
    ACCESS not-accessible
    STATUS mandatory
    DESCRIPTION
        "An entry is created for each feature that employs the
        error-disable feature."
    INDEX { cErrDisableFeatureIndex }
    ::= { cErrDisableFeatureTable 1 }

CErrDisableFeatureEntry ::= SEQUENCE {
    cErrDisableFeatureIndex CErrDisableFeatureID,
    cErrDisableFeatureConfigurable OCTET STRING,
    cErrDisableFeatureDetectEnable TruthValue,
    cErrDisableFeatureRecoveryEnable TruthValue,
    cErrDisableFeatureRecoveryInterval TimeIntervalSec,
    cErrDisableFeatureDetectShutdownVlan TruthValue,
    cErrDisableFeatureMaxFlapCount Gauge,
    cErrDisableFeatureFlapTimePeriod Gauge
    }

cErrDisableFeatureIndex OBJECT-TYPE
    SYNTAX CErrDisableFeatureID
--    Rsyntax INTEGER {
--        udld(1),
--        bpduGuard(2),
--        channelMisconfig(3),
--        pagpFlap(4),
--        dtpFlap(5),
--        linkFlap(6),
--        l2ptGuard(7),
--        dot1xSecurityViolation(8),
--        portSecurityViolation(9),
--        gbicInvalid(10),
--        dhcpRateLimit(11),
--        unicastFlood(12),
--        vmps(13),
--        stormControl(14),
--        inlinePower(15),
--        arpInspection(16),
--        portLoopback(17),
--        packetBuffer(18),
--        macLimit(19),
--        linkMonitorFailure(20),
--        oamRemoteFailure(21),
--        dot1adIncompEtype(22),
--        dot1adIncompTunnel(23),
--        sfpConfigMismatch(24),
--        communityLimit(25),
--        invalidPolicy(26),
--        lsGroup(27),
--        ekey(28),
--        portModeFailure(29),
--        pppoeIaRateLimit(30),
--        oamRemoteCriticalEvent(31),
--        oamRemoteDyingGasp(32),
--        oamRemoteLinkFault(33),
--        mvrp(34),
--        tranceiverIncomp(35)
--        }
    ACCESS not-accessible
    STATUS mandatory
    DESCRIPTION
        "This object uniquely identifies a feature that makes
        use of the error-disable feature."
    ::= { cErrDisableFeatureEntry 1 }

cErrDisableFeatureConfigurable OBJECT-TYPE
    SYNTAX OCTET STRING(SIZE(1..2))
        -- BITS are:
        --   detectionEnable(0)
        --   recoveryEnable(1)
        --   recoveryInterval(2)
        --   detectShutdownVlan(3)
        --   flapControl(4)
    ACCESS read-only
    STATUS mandatory
    DESCRIPTION
        "This object indicates whether the error-disable related
        configuration is configurable for this feature. If a bit
        is set to 1, then the corresponding error-disable
        configuration can be configured.
        
        'detectionEnable'    - indicates the error-disable detection
                               can be enabled/disabled for this feature
                               via cErrDisableFeatureDetectEnable.
        'recoveryEnable'     - indicates the error-disable recovery
                               can be enabled/disabled for this feature
                               via cErrDisableFeatureRecoveryEnable.
        'recoveryInterval'   - indicates the error-disable recovery
                               Interval can be configured via
                               cErrDisableFeatureRecoveryInterval.
        'detectShutdownVlan' - indicates the error-disable detection
                               shutdown vlan mode can be configured for
                               this feature via 
                               cErrDisableFeatureDetectShutdownVlan. 
        'flapControl'        - indicates the error-disable flap control
                               can be configured via 
                               cErrDisableFeatureMaxFlapCount and
                               cErrDisableFeatureFlapTimePeriod."
    ::= { cErrDisableFeatureEntry 2 }

cErrDisableFeatureDetectEnable OBJECT-TYPE
    SYNTAX TruthValue
--    Rsyntax INTEGER {
--        true(1),
--        false(2)
--        }
    ACCESS read-write
    STATUS mandatory
    DESCRIPTION
        "This object specifies whether the error-disable detection
        is enabled for the feature.
        
        Note:
           This object is read-write only for those features
           that are configurable, meaning:
           cErrDisableFeatureConfigurable.<featureIndex> has the
           first bit set to 1."
    ::= { cErrDisableFeatureEntry 3 }

cErrDisableFeatureRecoveryEnable OBJECT-TYPE
    SYNTAX TruthValue
--    Rsyntax INTEGER {
--        true(1),
--        false(2)
--        }
    ACCESS read-write
    STATUS mandatory
    DESCRIPTION
        "This object specifies whether the system can
        automatically recover a system entity that has been
        disabled by the feature."
    ::= { cErrDisableFeatureEntry 4 }

cErrDisableFeatureRecoveryInterval OBJECT-TYPE
    SYNTAX TimeIntervalSec
--    Rsyntax Gauge
    ACCESS read-write
    STATUS mandatory
    DESCRIPTION
        "This object specifies the error-recovery time interval
        that will be used by the system for any system entity that
        is error-disabled by this particular feature.
        
        If the value of this object is '0', then the device will
        use the value specified by the global configuration object
        cErrDisableRecoveryInterval."
    ::= { cErrDisableFeatureEntry 5 }

cErrDisableFeatureDetectShutdownVlan OBJECT-TYPE
    SYNTAX TruthValue
--    Rsyntax INTEGER {
--        true(1),
--        false(2)
--        }
    ACCESS read-write
    STATUS mandatory
    DESCRIPTION
        "This object specifies whether shutting down the violating
        VLAN on an interface is enabled or not. The value of 'true'
        indicates that shutting down the violating VLAN on an 
        interface is enabled. The value of 'false' indicates that 
        shutting down the violating VLAN on an interface is 
        disabled."
    ::= { cErrDisableFeatureEntry 6 }

cErrDisableFeatureMaxFlapCount OBJECT-TYPE
    SYNTAX Gauge
    ACCESS read-write
    STATUS mandatory
    DESCRIPTION
        "This object specifies the maximum number of flaps that
        are allowed to occur before setting to error disable state.
        A read-only value of zero indicates that no flap control
        is present."
    ::= { cErrDisableFeatureEntry 7 }

cErrDisableFeatureFlapTimePeriod OBJECT-TYPE
    SYNTAX Gauge
    ACCESS read-write
    STATUS mandatory
    DESCRIPTION
        "This object specifies the period of time counting the number of
        flaps that are allowed before setting to error disable state.
        A read-only value of zero indicates that no flap control
        is present."
    ::= { cErrDisableFeatureEntry 8 }

cErrDisableIfStatusTable OBJECT-TYPE
    SYNTAX SEQUENCE OF CErrDisableIfStatusEntry
    ACCESS not-accessible
    STATUS mandatory
    DESCRIPTION
        "This table provides interface (port) specific
        error-disable status information. Each conceptual row
        provides status information about a {interface, vlan}
        disabled by a feature.
        
        On a trunk or multi-vlan access interface, a given vlan on
        the interface can be error-disabled. In this case, the row is
        indexed by the ifIndex for the interface and the vlan
        index corresponding to the vlan in question.
        
        If the interface is carrying only 1 vlan or the entire
        trunk interface is error-disabled (due to link flaps, for
        example) then the vlan index portion of the row index is
        0."
    ::= { cErrDisableIfObjects 1 }

cErrDisableIfStatusEntry OBJECT-TYPE
    SYNTAX CErrDisableIfStatusEntry
    ACCESS not-accessible
    STATUS mandatory
    DESCRIPTION
        "A collection of objects that specify the status of an
        error-disabled Interface or {interface, vlan}."
    INDEX { ifIndex, cErrDisableIfStatusVlanIndex }
    ::= { cErrDisableIfStatusTable 1 }

CErrDisableIfStatusEntry ::= SEQUENCE {
    cErrDisableIfStatusVlanIndex VlanIndexOrZero,
    cErrDisableIfStatusCause CErrDisableFeatureID,
    cErrDisableIfStatusTimeToRecover TimeIntervalSec
    }

cErrDisableIfStatusVlanIndex OBJECT-TYPE
    SYNTAX VlanIndexOrZero
--    Rsyntax INTEGER(0..4095)
    ACCESS not-accessible
    STATUS mandatory
    DESCRIPTION
        "This object specifies the vlan of the given interface
        that has been error-disabled. If the physical interface is
        error-disabled then the value of this object is 0."
    ::= { cErrDisableIfStatusEntry 1 }

cErrDisableIfStatusCause OBJECT-TYPE
    SYNTAX CErrDisableFeatureID
--    Rsyntax INTEGER {
--        udld(1),
--        bpduGuard(2),
--        channelMisconfig(3),
--        pagpFlap(4),
--        dtpFlap(5),
--        linkFlap(6),
--        l2ptGuard(7),
--        dot1xSecurityViolation(8),
--        portSecurityViolation(9),
--        gbicInvalid(10),
--        dhcpRateLimit(11),
--        unicastFlood(12),
--        vmps(13),
--        stormControl(14),
--        inlinePower(15),
--        arpInspection(16),
--        portLoopback(17),
--        packetBuffer(18),
--        macLimit(19),
--        linkMonitorFailure(20),
--        oamRemoteFailure(21),
--        dot1adIncompEtype(22),
--        dot1adIncompTunnel(23),
--        sfpConfigMismatch(24),
--        communityLimit(25),
--        invalidPolicy(26),
--        lsGroup(27),
--        ekey(28),
--        portModeFailure(29),
--        pppoeIaRateLimit(30),
--        oamRemoteCriticalEvent(31),
--        oamRemoteDyingGasp(32),
--        oamRemoteLinkFault(33),
--        mvrp(34),
--        tranceiverIncomp(35)
--        }
    ACCESS read-only
    STATUS mandatory
    DESCRIPTION
        "This object specifies the feature/event that caused the
        {interface, vlan} (or the entire interface) to be
        error-disabled."
    ::= { cErrDisableIfStatusEntry 2 }

cErrDisableIfStatusTimeToRecover OBJECT-TYPE
    SYNTAX TimeIntervalSec
--    Rsyntax Gauge
    ACCESS read-only
    STATUS mandatory
    DESCRIPTION
        "Time left before the system attempts an automatic
        recovery of the interface or the vlan of the given 
        interface. If no recovery is scheduled, then the value 
        of this object is '0'."
    ::= { cErrDisableIfStatusEntry 3 }

cErrDisableInterfaceEvent TRAP-TYPE
--?? Non-reverse mappable trap
    ENTERPRISE cErrDisableNotificationsPrefix
    VARIABLES {
        cErrDisableIfStatusCause }
--  Status
--    deprecated
    DESCRIPTION
        "The cErrDisableInterfaceEvent is generated when an interface
        or {interface, vlan} is error-disabled by the feature
        specified in cErrDisableIfStatusCause.
        
        cErrDisableInterfaceEvent is deprecated and replaced by 
        cErrDisableInterfaceEventRev1."
    ::= 1

cErrDisableInterfaceEventRev1 TRAP-TYPE
-- Reverse mappable trap
    ENTERPRISE ciscoErrDisableMIB
    VARIABLES {
        cErrDisableIfStatusCause }
--  Status
--    mandatory
    DESCRIPTION
        "The cErrDisableInterfaceEventRev1 is generated when an
        interface or {interface, vlan} is error-disabled by the 
        feature specified in cErrDisableIfStatusCause.
        
        cErrDisableInterfaceEventRev1 deprecates 
        cErrDisableInterfaceEvent to make it RFC 2578 compliant. 
        According to section 8.5 of RFC 2578, the next
        to last sub-identifier in the name of any newly-defined
        notification must have the value zero."
    ::= 2

ciscoErrDisableGlobalCfgGroup OBJECT IDENTIFIER ::= { ciscoErrDisableMIBGroups 1 }
-- OBJECT-GROUP
--  Status
--    mandatory
--  Descr
--    A collection of objects to configure error-disable
--    functionality.
--  objects
--    cErrDisableRecoveryInterval

ciscoErrDisableFeatureCfgGroup OBJECT IDENTIFIER ::= { ciscoErrDisableMIBGroups 2 }
-- OBJECT-GROUP
--  Status
--    mandatory
--  Descr
--    A collection of objects to manage the configuration of
--    the error-disable feature.
--  objects
--    cErrDisableFeatureConfigurable, 
--    cErrDisableFeatureDetectEnable, 
--    cErrDisableFeatureRecoveryEnable, 
--    cErrDisableFeatureRecoveryInterval

ciscoErrDisableIfStatusGroup OBJECT IDENTIFIER ::= { ciscoErrDisableMIBGroups 3 }
-- OBJECT-GROUP
--  Status
--    mandatory
--  Descr
--    A collection of error-disable interface status objects.
--  objects
--    cErrDisableIfStatusCause, cErrDisableIfStatusTimeToRecover

ciscoErrDisableNotifCfgGroup OBJECT IDENTIFIER ::= { ciscoErrDisableMIBGroups 4 }
-- OBJECT-GROUP
--  Status
--    mandatory
--  Descr
--    A collection of objects to configure error-disable
--    notifications.
--  objects
--    cErrDisableNotifEnable, cErrDisableNotifRate

ciscoErrDisableShutdownVlanGroup OBJECT IDENTIFIER ::= { ciscoErrDisableMIBGroups 7 }
-- OBJECT-GROUP
--  Status
--    mandatory
--  Descr
--    A collection of objects to manage the configuration of
--    error-disable detection shutdown vlan mode.
--  objects
--    cErrDisableFeatureDetectShutdownVlan

ciscoErrDisableFeatureFlapGroup OBJECT IDENTIFIER ::= { ciscoErrDisableMIBGroups 8 }
-- OBJECT-GROUP
--  Status
--    mandatory
--  Descr
--    A collection of objects to manage the configuration of
--    the error-disable flap control.
--  objects
--    cErrDisableFeatureMaxFlapCount, 
--    cErrDisableFeatureFlapTimePeriod

ciscoErrDisableNotifGroup OBJECT IDENTIFIER ::= { ciscoErrDisableMIBGroups 5 }
-- NOTIFICATION-GROUP
--  Status
--    deprecated
--  Descr
--    A collection of error-disable notification objects.
--  notifications
--    cErrDisableInterfaceEvent

ciscoErrDisableNotifGroupRev1 OBJECT IDENTIFIER ::= { ciscoErrDisableMIBGroups 6 }
-- NOTIFICATION-GROUP
--  Status
--    mandatory
--  Descr
--    A collection of error-disable notification objects.
--  notifications
--    cErrDisableInterfaceEventRev1

ciscoErrDisableMIBCompliance OBJECT IDENTIFIER ::= { ciscoErrDisableMIBCompliances 1 }
-- MODULE-COMPLIANCE
--  Status
--    deprecated
--  Descr
--    The compliance statement for the cisco errdisable MIB.
--  Module
--    >>current<<
--   MandGroup
--    ciscoErrDisableGlobalCfgGroup
--   MandGroup
--    ciscoErrDisableFeatureCfgGroup
--   MandGroup
--    ciscoErrDisableIfStatusGroup
--   OptGroup
--    ciscoErrDisableNotifCfgGroup
--   OptGroup
--    ciscoErrDisableNotifGroup

ciscoErrDisableMIBComplianceRev1 OBJECT IDENTIFIER ::= { ciscoErrDisableMIBCompliances 2 }
-- MODULE-COMPLIANCE
--  Status
--    deprecated
--  Descr
--    The compliance statement for the cisco errdisable MIB.
--  Module
--    >>current<<
--   MandGroup
--    ciscoErrDisableGlobalCfgGroup
--   MandGroup
--    ciscoErrDisableFeatureCfgGroup
--   MandGroup
--    ciscoErrDisableIfStatusGroup
--   OptGroup
--    ciscoErrDisableNotifCfgGroup
--   OptGroup
--    ciscoErrDisableNotifGroupRev1
--   OptGroup
--    ciscoErrDisableShutdownVlanGroup
--   ObjVar
--    cErrDisableRecoveryInterval
--   ObjVar
--    cErrDisableNotifEnable
--   ObjVar
--    cErrDisableNotifRate
--   ObjVar
--    cErrDisableFeatureDetectEnable
--   ObjVar
--    cErrDisableFeatureRecoveryEnable
--   ObjVar
--    cErrDisableFeatureRecoveryInterval
--   ObjVar
--    cErrDisableFeatureDetectShutdownVlan

ciscoErrDisableMIBComplianceRev2 OBJECT IDENTIFIER ::= { ciscoErrDisableMIBCompliances 3 }
-- MODULE-COMPLIANCE
--  Status
--    mandatory
--  Descr
--    The compliance statement for the cisco errdisable MIB.
--  Module
--    >>current<<
--   MandGroup
--    ciscoErrDisableGlobalCfgGroup
--   MandGroup
--    ciscoErrDisableFeatureCfgGroup
--   MandGroup
--    ciscoErrDisableIfStatusGroup
--   OptGroup
--    ciscoErrDisableNotifCfgGroup
--   OptGroup
--    ciscoErrDisableNotifGroupRev1
--   OptGroup
--    ciscoErrDisableShutdownVlanGroup
--   OptGroup
--    ciscoErrDisableFeatureFlapGroup
--   ObjVar
--    cErrDisableRecoveryInterval
--   ObjVar
--    cErrDisableNotifEnable
--   ObjVar
--    cErrDisableNotifRate
--   ObjVar
--    cErrDisableFeatureDetectEnable
--   ObjVar
--    cErrDisableFeatureRecoveryEnable
--   ObjVar
--    cErrDisableFeatureRecoveryInterval
--   ObjVar
--    cErrDisableFeatureDetectShutdownVlan
--   ObjVar
--    cErrDisableFeatureMaxFlapCount
--   ObjVar
--    cErrDisableFeatureFlapTimePeriod


END
