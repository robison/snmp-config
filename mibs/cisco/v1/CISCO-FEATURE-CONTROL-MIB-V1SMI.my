-- MIB file created 09-Apr-2014 16:31:41, by
--   SMICng version 2.2.11-beta(PRO)(Solaris), January 20, 2001. Enterprise key cisco.com

CISCO-FEATURE-CONTROL-MIB DEFINITIONS ::= BEGIN

-- From file: "CISCO-FEATURE-CONTROL-MIB.my"
-- Compile options "4 7 F H N W 03 06 0B 0G 0N 0T"

IMPORTS
    TruthValue
            FROM SNMPv2-TC-v1
    SnmpAdminString
            FROM SNMP-FRAMEWORK-MIB
    ciscoMgmt
            FROM CISCO-SMI
    Gauge
            FROM RFC1155-SMI
    OBJECT-TYPE
            FROM RFC-1212
    TRAP-TYPE
            FROM RFC-1215;

ciscoFeatureCtrlMIB OBJECT IDENTIFIER ::= { ciscoMgmt 377 }
-- MODULE-IDENTITY
--  LastUpdated
--    201404090000Z
--  OrgName
--    Cisco Systems, Inc.
--  ContactInfo
--    Cisco Systems
--    Customer Service
--    
--    Postal: 170 W Tasman Drive
--    San Jose, CA  95134
--    USA
--    
--    Tel: +1 800 553-NETS
--    
--    E-mail:  cs-san@cisco.com
--  Descr
--    There are two types of features in the system:
--    
--    - Regular features
--    - Optional features
--    
--    The Regular features may or may not need to support
--    the user triggerd control (enabling/disabling). In
--    case the regular features need to  support such 
--    control, they need to be instrumented in their 
--    respective MIBs.
--    
--    The Optional features can be controlled (enabled/
--    disabled) by the user via CLI/SNMP. The optional
--    features are generally disabled by default. As part
--    of the enabling of such optional feature, the first
--    mandatory step is to explicitly enable the feature
--    using the CLI/SNMP. Following this mandatory step, 
--    a feature may require additional feature specific
--    enabling steps similar to the regular features.
--    In addition to the user triggered control, other 
--    system specific conditions like licensing may
--    influence the operating state of such optional 
--    feature. 
--    
--    This MIB module is to facilitate the global level 
--    control (enabling/disabling) over the optional 
--    features in the system. The disabling of such 
--    optional feature using this MIB module would make
--    the feature disabled and the entire feature specific
--    mib objects also unavailable.
--    
--    Glossary of the terms used in this MIB:
--    
--    VSAN - Virtual Storage Area Network, similar to 
--           a VLAN.
--    
--    WWN  - World Wide Name. Mechanism of identifying
--           devices in Fibre Channel Networks. It is
--           8 bytes long.
--    
--    AAA - Authentication, Authorization and Accounting
--    
--    FLOGI - Fibre Channel fabric login
--    
--    MDS -  Multilayer Director Switch
--  RevDate
--    201404090000Z
--  RevDescr
--    Updated 'CiscoOptionalFeature' TC for
--    following features:
--    vff, sol, mplsStatic, nxapi, itd, vmTracker.
--    Updated 'CiscoOptionalFeatureSet' TC for 
--    feature-set Fabric
--  RevDate
--    201307290000Z
--  RevDescr
--    Updated 'CiscoOptionalFeature' TC for
--       following features: 
--    fabricAccess
--  RevDate
--    201305280000Z
--  RevDescr
--    Updated 'CiscoOptionalFeature' TC for
--       following features:
--        vTracker, fdmi, cmm, ntp, fabricMgr, 
--        nat, vlanVnSeg, bulkStat, bbu, vnSegment,
--        evb, ngMvpn, hmm, vxlan, mvrp, evmed, 
--        nSegMgr, poap
--  RevDate
--    201203220000Z
--  RevDescr
--    Updated 'CiscoOptionalFeature' TC for
--    following features:
--      fex, pong, rtp, ldap, privilege, oim,
--      mplsMgr, ulib, scp, sftp, l3vpn,
--      meshSecurity, mvpn, ipPool, uufb,
--      umfb, ethernetNpv, wccpClient,
--      scadaGw, poe, flexLink, niv,
--      vem, ewise, onep, slaS, slaR,
--      rise, pppManager, itronmcastagent,
--     vsmaggregation, segmentation, vrrpv3
--  RevDate
--    201106090000Z
--  RevDescr
--    Added CiscoOptionalFeatureSet TC;
--    Modified CiscoFeatureAction TC to include enum values 
--        of install(4), uninstall(5), allow(6), disallow(7); 
--    Modified CiscoFeatureStatus TC to include enum values 
--        of installed(4), uninstalled(5); 
--    Added cfcFeatureSetGroup,
--        cfcFeatureSetNotificationCtrlGroup, 
--        and cfcFeatureSetNotificationGroup.
--  RevDate
--    200908110000Z
--  RevDescr
--    Updated 'CiscoOptionalFeature' TC for
--    following features:
--     telnetServer, sshServer, httpServer, wccp, siaSve,
--     xcvrFreq, assocMgr, lldp, rsvp, ldp, te, mplsOam,
--     l2vpn, drap, bfd, bfdApp, fex
--  RevDate
--    200812050000Z
--  RevDescr
--    Updated 'CiscoOptionalFeature' TC for
--    following features:
--     evfp, vtp, splitter, sfm, ioa
--  RevDate
--    200806270000Z
--  RevDescr
--    Updated 'CiscoOptionalFeature' TC for
--    the 'siaServiceBroker' feature.
--  RevDate
--    200806120000Z
--  RevDescr
--    Synced up the mib and feature-ids used
--    in different branches.
--    
--    Reordered following features in
--    'CiscoOptionalFeature' TC:
--    
--    lacp, amt, dot1x, l2nac.
--    
--    Renamed following features in
--    'CiscoOptionalFeature' TC:
--    
--    fcNportMux to npv
--    
--    Deleted following features in
--    'CiscoOptionalFeature' TC:
--    
--    fc
--    
--    Added following features in
--    'CiscoOptionalFeature' TC:
--    
--    cluster, glbp, dhcpSnooping, hsrp, svi,
--    vmm, pvlan, tunnelManager, ethPortSec,
--    lisp, trustSec, copp, udld, mcecm, pbr,
--    nfm, isapi, vrrp, netSift, isisL2,
--    cimServer, otv, sanTap, nasb, dmm,
--    u2rib, isisOtv, orib, fcoe.
--  RevDate
--    200803130000Z
--  RevDescr
--    Updated 'CiscoOptionalFeature' TC for
--    the 'fc' feature.
--  RevDate
--    200705040000Z
--  RevDescr
--    Updated 'CiscoOptionalFeature' TC for
--    the 'fcNportMux' feature.
--  RevDate
--    200701220000Z
--  RevDescr
--    Added new table cfcFeatureCtrl2Table which deprecates
--    cfcFeatureCtrlTable to provide multiple feature 
--    instance support. Updated the CiscoOptionalFeature TC.   
--    Added the new notification ciscoFeatOpStatusChange.   
--    Added the new Module Compliance 
--    ciscoFeatureCtrlMIBComplianceRev and new conformance 
--    groups cfcFeatureGroupRev and cfcNotificationGroupRev.
--  RevDate
--    200512270000Z
--  RevDescr
--    Updated 'CiscoOptionalFeature' TC for
--    the 'cloudDiscovery' feature.
--  RevDate
--    200412280000Z
--  RevDescr
--    Updated 'CiscoOptionalFeature' TC for
--    the 'extendedCredit' feature.
--  RevDate
--    200407060000Z
--  RevDescr
--    Updated 'CiscoOptionalFeature' TC for the following
--    new optional features:
--              - ike
--              - isns
--              - ipSec
--              - portTracker
--              - scheduler
--              - npiv
--              - sanExtTuner
--              - dpvm
--  RevDate
--    200311220000Z
--  RevDescr
--    Initial version of this MIB.

ciscoFeatureCtrlMIBNotifs OBJECT IDENTIFIER ::= { ciscoFeatureCtrlMIB 0 }
ciscoFeatureCtrlMIBObjects OBJECT IDENTIFIER ::= { ciscoFeatureCtrlMIB 1 }
ciscoFeatureCtrlMIBConformance OBJECT IDENTIFIER ::= { ciscoFeatureCtrlMIB 2 }
cfcFeature      OBJECT IDENTIFIER ::= { ciscoFeatureCtrlMIBObjects 1 }
cfcNotifControl OBJECT IDENTIFIER ::= { ciscoFeatureCtrlMIBObjects 2 }
ciscoFeatureCtrlMIBCompliances OBJECT IDENTIFIER ::= { ciscoFeatureCtrlMIBConformance 1 }
ciscoFeatureCtrlMIBGroups OBJECT IDENTIFIER ::= { ciscoFeatureCtrlMIBConformance 2 }

CiscoOptionalFeature ::= INTEGER {
        ivr(1),
        fcip(2),
        fcsp(3),
        ficon(4),
        iscsi(5),
        tacacs(6),
        qosManager(7),
        portSecurity(8),
        fabricBinding(9),
        iscsiInterfaceVsanMembership(10),
        ike(11),
        isns(12),
        ipSec(13),
        portTracker(14),
        scheduler(15),
        npiv(16),
        sanExtTuner(17),
        dpvm(18),
        extenedCredit(19),
        cloudDiscovery(20),
        isis(21),
        ospf(22),
        ospfV3(23),
        rip(24),
        bgp(25),
        pim(26),
        igmp(27),
        msdp(28),
        pim6(29),
        eigrp(30),
        sdv(31),
        cluster(32),
        sme(33),
        lacp(34),
        amt(35),
        dot1x(36),
        npv(37),
        l2nac(38),
        glbp(39),
        dhcpSnooping(40),
        hsrp(41),
        svi(42),
        vmm(43),
        pvlan(44),
        tunnelManager(45),
        ethPortSec(46),
        lisp(47),
        trustSec(48),
        copp(49),
        udld(50),
        mcecm(51),
        pbr(52),
        nfm(53),
        isapi(54),
        vrrp(55),
        netSift(56),
        isisL2(57),
        cimServer(58),
        otv(59),
        sanTap(60),
        nasb(61),
        dmm(62),
        u2rib(63),
        isisOtv(64),
        orib(65),
        fcoe(66),
        siaServiceBroker(67),
        evfp(68),
        vtp(69),
        splitter(70),
        sfm(71),
        ioa(72),
        telnetServer(73),
        sshServer(74),
        httpServer(75),
        wccp(76),
        siaSve(77),
        xcvrFreq(78),
        assocMgr(79),
        lldp(80),
        rsvp(81),
        ldp(82),
        te(83),
        mplsOam(84),
        l2vpn(85),
        drap(86),
        bfd(87),
        bfdApp(88),
        fex(89),
        pong(90),
        rtp(91),
        ldap(92),
        privilege(93),
        oim(94),
        mplsMgr(95),
        ulib(96),
        scp(97),
        sftp(98),
        l3vpn(99),
        mvpn(101),
        ipPool(102),
        uufb(103),
        umfb(104),
        ethernetNpv(105),
        wccpClient(106),
        scadaGw(107),
        poe(108),
        flexlink(109),
        niv(110),
        vem(111),
        ewise(112),
        onep(113),
        slaS(114),
        slaR(115),
        rise(116),
        pppManager(117),
        itronMcastAgent(118),
        vsmAggregation(119),
        segmentation(120),
        vrrpv3(121),
        vTracker(122),
        fdmi(123),
        cmm(124),
        ntp(125),
        fabricAccess(126),
        nat(127),
        vlanVnSeg(128),
        bulkStat(129),
        bbu(130),
        vnSegment(131),
        evb(132),
        ngMvpn(134),
        hmm(135),
        vxlan(136),
        mvrp(137),
        evmed(138),
        nSegMgr(139),
        vff(140),
        sol(141),
        mplsStatic(142),
        nxapi(143),
        itd(144),
        vmTracker(145),
        poap(200)
        }
-- TEXTUAL-CONVENTION
--  Status
--    mandatory
--  Descr
--    The optional features in the sytem.
--    
--    ivr(1)            - Inter VSAN Routing
--    
--    fcip(2)           - Fibre Channel over IP Protocol
--    
--    fcsp(3)           - Fibre Channel Security Protocol
--    
--    ficon(4)          - Fibre Connectivity interface
--    
--    iscsi(5)          - iSCSI (Internet Small Computer 
--                        System Interface) protocol
--    
--    tacacs(6)         - Tacacs+ AAA protocol
--    
--    qosManager(7)     - Quality Of Service
--    
--    portSecurity(8)   - Port Security
--    
--    fabricBinding(9)  - Fabric Binding
--    
--    iscsiInterfaceVsanMembership(10) - iSCSI-Interface-VSAN
--                                       membership
--    
--    ike(11)           - Internet Key Exchange feature. This
--                        is used to negotiate cryptographic
--                        keys for IPsec traffic
--    
--    isns(12)          - iSNS (Internet Storage Name Service)
--                        server. This provides name service,
--                        access control and state change 
--                        notifications for iSCSI devices
--    
--    ipsec(13)         - IPSec security services on the device
--    
--    portTracker(14)   - Port Tracker. This allows ports to be
--                        brought down and up based on changes
--                        in the port states of certain 
--                        configured (tracked) ports
--    
--    scheduler(15)     - Scheduler feature provides jobs to be 
--                        scheduled at a specified time. A Job is
--                        a collection of configuration commands
--                        in the device.
--    
--    npiv(16)          - Nx_Port ID Virtualization. This is a 
--                        mechanism by which a N_Port can get more
--                        than one Nx_Port_Id from the fibre 
--                        channel (FC) fabric
--    
--    sanExtTuner(17)   - SAN Extension Tuner. This is a tool 
--                        used to generate and analyze SCSI 
--                        workloads across the FCIP tunnels. 
--                        This can be used to tune the FCIP
--                        tunnels for desired throughput.
--    
--    dpvm(18)          - Dynamic Port Vsan Membership. This 
--                        manages allocation of VSAN to a port 
--                        based on the device WWN at the time of
--                        device FLOGI
--    
--    extenedCredit(19) - Extended Credit feature. This provides
--                        a way to increase the receive buffer
--                        to buffer credits on physical FC Ports
--    
--    cloudDiscovery(20)- This feature provides grouping 
--                        functionality of all the IP networks 
--                        connected to the various gigabit 
--                        ethernet interfaces in a 'Fabric'
--    
--    isis(21)          - IS-IS Unicast Routing Protocol
--    
--    ospf(22)          - Open Shortest Path First Unicast Routing
--                        Protocol
--    
--    ospfV3(23)        - Open Shortest Path First Version 3 Unicast
--                        Routing Protocol
--    
--    rip(24)           - Routing Information Protocol
--    
--    bgp(25)           - Border Gateway Protocol
--    
--    pim(26)           - Protocol Independent Multicast
--    
--    igmp(27)          - Internet Group Management Protocol
--    
--    msdp(28)          - Multicast Source Discovery Protocol
--    
--    pim6(29)          - Protocol Independent Multicast (PIM) for
--                        IPv6
--    
--    eigrp(30)         - Enhanced Interior Gateway Routing Protocol
--    
--    sdv(31)           - SAN Device-Virtualization Manager
--    
--    cluster(32)       - This feature provides a common
--                        infrastructure for distributed applications
--                        running on multiple switches.  It provides
--                        consistency and replication of application
--                        metadata. It also handles membership and
--                        quorum service.
--    
--    sme(33)           - SME Daemon
--    
--    lacp(34)          - Link Aggregation Control Protocol
--    
--    amt(35)           - Auto-Multicast Tunneling
--    
--    dot1x(36)         - DOT1X Daemon
--    
--    
--    npv(37)           - FC N_port Multiplexer allows multiple
--                        end-devices on a switch which does not
--                        require a domain_ID to login to a
--                        NPIV-capable switch and thereby
--                        communicate with other devices in the 
--                        fabric.
--    
--    l2nac(38)         - L2NAC Daemon
--    
--    glbp(39)          - Gateway Load Balancing Protocol. This
--                        protocol provides support for gateway
--                        redundancy and in load balancing traffic.
--    
--    
--    dhcpSnooping(40)  - Handles dhcp snooping, IP source guard
--                        and Dynamic ARP Inspection (DAI)
--                        functionality.
--    
--    hsrp(41)          - The Hot Standby Router Protocol, HSRP,
--                        provides a mechanism which is designed
--                        to support non-disruptive failover of
--                        IP traffic in certain circumstances.
--                        In particular, the protocol protects
--                        against the failure of the first hop
--                        router when the source host cannot
--                        learn the IP address of the first hop
--                        router dynamically.
--    
--    
--    svi(42)           - Switch Virtual Interface Manager
--    
--    vmm(43)           - Virtual Module Manager
--    
--    pvlan(44)         - Private Vlan Manager
--    
--    tunnelManager(45) - Tunnel manager manages tunnel interfaces
--                        which includes creation, configuration
--                        and deletion of a tunnel interface.
--    
--    ethPortSec(46)    - Ethernet Port Security provides a MAC
--                        based security feature for L2 ports.
--    
--    lisp(47)          - Locator ID Separation Protocol
--    
--    trustSec(48)      - Cisco TrustSec. Provides authentication,
--                        authorization, encryption and SGACLs 
--                        (Security Group Access Control Lists).
--    
--    copp(49)          - Control Plane Policing.
--    
--    udld(50)          - Unidirectional link-detection to ensure
--                        ethernet link is working properly
--    
--    mcecm(51)         - Multi-Chassis Ether-Channel Manager
--    
--    pbr(52)           - PBR uses route-maps to provide policy
--                        based routing functionality. 
--    
--    nfm(53)           - NetFlow provides a key set of services for
--                        IP applications, including network traffic
--                        accounting, usage-based network billing,
--                        network planning, security, Denial of
--                        Service monitoring capabilities, and
--                        network monitoring. NetFlow provides
--                        valuable information about network users
--                        and applications, peak usage times, and
--                        traffic routing.
--    
--    isapi(54)         - This service is a conditional service and
--                        enables the various storage applications
--                        running on the ISAPI (Intelligent Switch
--                        API).
--    
--    vrrp(55)          - The Virtual Router Redundancy Protocol,
--                        VRRP, provides a mechanism to eliminate
--                        the single point of failure as present
--                        in default static routed environments.
--                        Redundancy is provided in using any of the
--                        virtual router's IP addresses as the 
--                        default first hop router by hosts 
--                        in the LAN.
--    
--    netSift(56)       - Enable Netsift features of DPI (Deep Packet
--                        Inspection) and measurements.
--    
--    isisL2(57)        - This feature implements the control
--                        plane for DCE (Data Center Ethernet). It
--                        provides both unicast and multicast routes
--                        to the RIBs (Routing Information Bases) for
--                        forwarding DCE frames. 
--    
--    cimServer(58)     - CISCO's Web Based Enterprise Management 
--                        (WBEM) Services daemon process.
--    
--    otv(59)           - This feature is provides control plane
--                        functionality for OTV (Overlay Transport
--                        Virtualization).
--    
--    sanTap(60)        - SanTap is a fibre channel switch based
--                        capability that provides a reliable copy
--                        of the data flowing between a set of one
--                        or more initiators and a set of one or
--                        more targets connected to the fabric.
--    
--    nasb(61)          - The TPC (Third-party Copy) or NASB (Network
--                        Accelerated Serverless Backup) feature
--                        exposes a disk target with Logical Unit
--                        Number(LUN) 0 that is capable of processing
--                        the SCSI Extended Copy Command (XCOPY) to
--                        transfer data from a specified source to a
--                        specified destination.
--    
--    dmm(62)           - DMM (Data Migration Manager) facilitates
--                        migration of data from one storage 
--                        subsystem to another.
--    
--    u2rib(63)         - Layer 2 unicast Routing Information Base
--                        component.
--    
--    isisOtv(64)       - IS-IS protocol for OTV (Overlay Transport
--                        Virtualization)
--    
--    orib(65)          - OTV (Overlay Transport Virtualization)
--                        Routing Information Base
--    
--    fcoe(66)          - Fiber Channel over Ethernet.
--    
--    siaServiceBroker(67) - Nexus Service Insertion Architecture.
--    
--    evfp(68)          - Trunking F_Ports and F_Port-Channels.
--    
--    vtp(69)           - Vlan Trunking Protocol
--    
--    splitter(70)      - FCoE (Fiber Channel over Ethernet) traffic
--                        splitter
--    
--    sfm(71)           - SCSI (Small Computer serial interface) flow
--                        manager used for enabling Fibre Channel
--                        Write Acceleration on SSM (Storage Services
--                        Module) cards
--    
--    ioa(72)           - This feature allows more flexible I/O
--                        acceleration services such as write
--                        acceleration or tape acceleration
--    
--    telnetServer(73)  - Telnet Server
--    
--    sshServer(74)     - SSH Server
--    
--    httpServer(75)    - HTTP Server
--    
--    wccp(76)          - Web Cache Communication Protocol for
--    Nexus7k
--    
--    siaSve(77)        - SIA Services Virtualization Endpoint
--    
--    xcvrFreq (78)     - X2 Transceiver Frequency configuration
--    
--    assocMgr(79)      - The feature enables VLAN <==> VSAN 
--                        translation and acts as a bridge between 
--                        LAN and SAN world. It manages the mappings 
--                        of VLANs with associated VSANs and 
--                        vice versa
--    
--    lldp(80)          - Link Layer Discovery Protocol
--    
--    rsvp(81)          - Implements the RSVP protocol that is 
--                        used to make resource reservations for 
--                        an application for example MPLS/TE
--    
--    ldp(82)            - MPLS Label Distribution Protocol
--    
--    te(83)             - MPLS Traffic Engineering
--    
--    mplsOam(84)        - MPLS Operations and Management
--    
--    l2vpn(85)          - Layer2 VPN
--    
--    drap(86)           - DRAP
--    
--    bfd(87)            - BFD
--    
--    bfdApp(88)         - BFD_APP
--    
--    fex(89)            - FEX
--    
--    pong(90)           - Layer 2 connectivity and latency 
--                         measurement tool based on 1588 
--                         constructs
--    
--    rtp(91)            - Real-time Transport Protocol 
--    
--    ldap(92)           - Lightweight Directory Access Protocol
--    
--    privilege(93)      - Enable IOS like privilege support 
--                         for authorization
--    
--    oim(94)            - The interface manager for advanced 
--                         features like OTV, TE, mVPN etc
--    
--    mplsMgr(95)       - Manages general MPLS related functionality
--    
--    ulib(96)           - Unified label information base 
--                         responsible for the storage of 
--                         MPLS label forwarding information
--    
--    scp(97)            - scp protocal
--    
--    sftp(98)           - sftp protocal
--    
--    l3vpn(99)          - Layer 3 Virtual Private Networks
--    
--    mvpn(101)          - Provides multicast service if customer 
--                         sites are partitioned
--    
--    ipPool(102)       - Creates and manages the IP Address
--    
--    uufb(103)          - Unknown Unicast Flood Blocking
--    
--    umfb(104)          - Unknown Multicast Flood Blocking
--    
--    ethernetNpv(105)  - An enhanced form of FIP snooping over 
--                        an ethernet bridge connecting FCoE 
--                        hosts to FCoE FCF  
--    
--    wccpClient(106)   - Web Cache Communication Protocol Client
--    Side
--    
--    scadaGw(107)      - scada protocol translations
--    
--    poe(108)           - Power over Ethernet
--    
--    flexlink(109)      - Manager process for switchport 
--                         backup feature
--    
--    niv(110)           - Network Interface Virtualization 
--    
--    vem(111)           - Virtual Ethernet Module
--    
--    ewise(112)         - Energywise for N7K
--    
--    onep(113)          - Allows third parties to create 
--                         network applications
--    
--    slaS(114)         - SLA sender
--    
--    slaR(115)         - SLA receiver
--    
--    rise(116)         - rise feature enables tighter
--                        integration with the Nexus 7000 
--                        for attached Cisco appliances that 
--                        support Remote Integrated Service 
--                        Extenders (RISE) functionality
--    
--    pppManager(117)   - Point-to-point protocol manager 
--                        creates and manages of Point-to-Point 
--                        protocol instances
--    
--    itronMcastAgent(118) - This is a process listens for multicast 
--                           traffic and implement the itron specify 
--                           reliability protocol over smart grid RF 
--                           networks
--    
--    vsmAggregation(119) - VSM aggregation feature on Cisco 
--                          Nexus 1000v enables multiple N1K 
--                          control planes to be combined to 
--                          manage a single DVS (distributed 
--                          virtual switch)
--    
--    segmentation(120)   - Vxlan feature on Cisco Nexus 
--                          1000v enables scalable cloud 
--                          architecture with replicated 
--                          server pods in different subnets.
--                          It provides a means to stretch 
--                          a layer 2 network by using a 
--                          layer 2 overlay scheme over 
--                          a layer 3 network
--    
--    vrrpv3(121)         - The Virtual Router Redundancy 
--                          Protocol version 3, dynamically 
--                          assign responsibility for routing 
--                          to one of a group of routers 
--                          participating in the protocol. 
--                          VRRPv3 supports both IPv4 and IPv6
--    
--    vTracker(122)  - vTracker feature allows network-admin to view 
--           and monitor the virtualized environment in a data-center network. 
--           It also enables the network-admin to get the attributes
--           of servers and virtual machines from the hypervisor 
--           management framework such as Vcenter for VMware. 
--           
--    fdmi(123)   - FDMI feature allows network-admin to view and monitor 
--           Fabric devices like Host Bus Adaptors in a data center network.
--          
--    cmm(124)   - Cable Management Manager feature on allows auto detection 
--           of cabling errors in clos and non-clos network designs. 
--          
--    ntp(125)   - Network Time Protocol feature allows clock
--           synchronization of router to other servers and 
--           clients.
--    
--    fabricAccess(126) - Single point of Access feature for the Fabric Network.  
--    
--    nat(127)   - IP Network Address Translation Manager
--    
--    vlanVnSeg(128)  - Vlan based vn-segment is a simplified multi-tenancy
--           solution in Vinci. This allows Vinci to support more 
--           than 4k tenants for the whole network but with limit(<4k)
--           for each leaf node.
--         
--    bulkStat(129)  - Bulk Stats Collection and Export feature 
--           is a solution to collect bulk/stats and export 
--           to NMS. This feature uses CM services to collect 
--           data and transfers raw and processed date to NMS.
--           
--    bbu(130)   - BBU is a Battery Backup Unit support feature on Smart 
--           Grid platforms.
--           
--    vnSegment(131)  - Multi-Tenancy and Virtual Network Segment(VN-Segment) 
--           allows the creation of virtual network segments to 
--           facilitate the creation and operation of virtual data 
--           centers. 
--           
--    evb(132)   - Edge Virtual Bridge feature is based on 802.1Qbg and 
--           defines the interaction between virtual switching environments
--           in a hypervisor and the first-layer in a switching environment.
--           
--    ngMvpn(134)   - Next Generation MVPN features. 
--    
--    hmm(135)    - Host Mobility Manager maintains local and 'remote interest'
--           host database, detects and tracks host/VM movement. 
--    
--    vxlan(136)   - Virtual Extensible LAN feature is an encapsulation protocol for
--           running an overlay network on existing Layer 3 infrastructure.
--    
--    mvrp(137)   - MVRP feature is an industry standard vlan-pruning
--           protocol. It helps in filtering unrequited traffic
--           downstream. 
--           
--    evmed(138)          - EVMED feature allows network-admin
--           to use EEM to monitor Application, Interface 
--           Statistics and TImer based events and schedule
--           actions on occurance of those events
--    
--    nSegMgr(139)   - Manage bridge domains as objects,
--          exposing them by providing APIs to external virtualization
--          servers such as VMware vCloud Director, Virtual Machine Manager
--          Openstack Quantum and Horizon.
--    
--    vff(140)   - Dynamic Forwarding Automation
--    
--    sol(141)   - Serial over LAN provides a mechanism which enables the serial controller
--          of a managed system to be redirected over an IPMI session using LAN packets.
--          
--    mplsStatic(142)  - MPLS static allows the allocation of labels and provisioning of label
--          switched paths through explicit configuration of labels and forwarding
--          information.
--          
--    nxapi(143)    - nxapi feature exposes CLIs that traditionally run on the switch to the outside 
--          of the switch through HTTP/HTTPs.
--        
--    itd(144)   - With Intelligent Traffic Director(ITD), customer can deploy service appliances from any vendors
--          with no Network/Topology change.
--          
--    vmTracker(145)  - vmTracker tracks all the virtual machines in a given system.
--                      
--    poap(200)   - Power-On Auto Provisioning     
--    .

CiscoOptionalFeatureSet ::= INTEGER {
        fcoe(1),
        l2mp(2),
        fex(3),
        mpls(4),
        fabric(7)
        }
-- TEXTUAL-CONVENTION
--  Status
--    mandatory
--  Descr
--    The optional feature Set in the sytem.
--    
--    fcoe(1)         - Fabric Channel over Ethernet
--    l2mp(2)         - Layer 2 Multipathing
--    fex(3)          - Fabric Extender
--    mpls(4)         - Multiprotocol Label Switching
--    fabric(7)  - Fabric Feature-set 
--    .

CiscoFeatureAction ::= INTEGER {
        noOp(1),
        enable(2),
        disable(3),
        install(4),
        uninstall(5),
        allow(6),
        disallow(7)
        }
-- TEXTUAL-CONVENTION
--  Status
--    mandatory
--  Descr
--    Action trigger for the feature.
--    
--    noOp(1)      - No operation           
--    enable(2)    - Enable the feature or feature set
--    disable(3)   - Disable the feature or feature set
--    install(4)   - Install the feature or feature set
--    uninstall(5) - Uninstall the feature or feature set
--    allow(6)     - Allow the feature or feature set to be enabled
--    disallow(7)  - Do not allow the feature or feature set to be
--    enabled
--    
--    .

CiscoFeatureStatus ::= INTEGER {
        unknown(1),
        enabled(2),
        disabled(3),
        installed(4),
        uninstalled(5)
        }
-- TEXTUAL-CONVENTION
--  Status
--    mandatory
--  Descr
--    Status of the feature or feature set.
--    
--    unknown(1)     - Unknown status
--    enabled(2)     - Feature or feature set is operational 
--                     and available
--    disabled(3)    - Feature or feature set is disabled 
--                     and not available
--    installed(4)   - Feature or feature set is installed
--    uninstalled(5) - Feature or feature set is uninstalled
--    
--    .

CiscoFeatureActionResult ::= INTEGER {
        none(1),
        actionSuccess(2),
        actionFailed(3),
        actionInProgress(4)
        }
-- TEXTUAL-CONVENTION
--  Status
--    mandatory
--  Descr
--    Result of the feature or feature set action.
--    
--    none(1)               - No action triggered           
--    actionSuccess(2)      - Execution of the action triggered 
--                            is completed Successfully
--    actionFailed(3)       - Execution of the action failed 
--    actionInProgress(4)   - Execution of the action  triggered
--                            is in progress
--    .

cfcFeatureCtrlTable OBJECT-TYPE
    SYNTAX SEQUENCE OF CfcFeatureCtrlEntry
    ACCESS not-accessible
    STATUS deprecated
    DESCRIPTION
        "A table consisting of entries for all the features that can
        be optionally enabled/disabled in the system. This table 
        provides administrative control and current operating state
        information of the feature.
        cfcFeatureCtrlTable object is superseded 
        by cfcFeatureCtrl2Table."
    ::= { cfcFeature 1 }

cfcFeatureCtrlEntry OBJECT-TYPE
    SYNTAX CfcFeatureCtrlEntry
    ACCESS not-accessible
    STATUS deprecated
    DESCRIPTION
        "An entry (conceptual row) in the 'cfcFeatureCtrlTable'.
        Each row represents an optional feature in the system.
        cfcFeatureCtrlEntry object is superseded 
        by cfcFeatureCtrl2Entry."
    INDEX { cfcFeatureCtrlIndex }
    ::= { cfcFeatureCtrlTable 1 }

CfcFeatureCtrlEntry ::= SEQUENCE {
    cfcFeatureCtrlIndex CiscoOptionalFeature,
    cfcFeatureCtrlName SnmpAdminString,
    cfcFeatureCtrlAction CiscoFeatureAction,
    cfcFeatureCtrlLastAction CiscoFeatureAction,
    cfcFeatureCtrlLastActionResult CiscoFeatureActionResult,
    cfcFeatureCtrlLastFailureReason SnmpAdminString,
    cfcFeatureCtrlOpStatus CiscoFeatureStatus,
    cfcFeatureCtrlOpStatusReason SnmpAdminString
    }

cfcFeatureCtrlIndex OBJECT-TYPE
    SYNTAX CiscoOptionalFeature
--    Rsyntax INTEGER {
--        ivr(1),
--        fcip(2),
--        fcsp(3),
--        ficon(4),
--        iscsi(5),
--        tacacs(6),
--        qosManager(7),
--        portSecurity(8),
--        fabricBinding(9),
--        iscsiInterfaceVsanMembership(10),
--        ike(11),
--        isns(12),
--        ipSec(13),
--        portTracker(14),
--        scheduler(15),
--        npiv(16),
--        sanExtTuner(17),
--        dpvm(18),
--        extenedCredit(19),
--        cloudDiscovery(20),
--        isis(21),
--        ospf(22),
--        ospfV3(23),
--        rip(24),
--        bgp(25),
--        pim(26),
--        igmp(27),
--        msdp(28),
--        pim6(29),
--        eigrp(30),
--        sdv(31),
--        cluster(32),
--        sme(33),
--        lacp(34),
--        amt(35),
--        dot1x(36),
--        npv(37),
--        l2nac(38),
--        glbp(39),
--        dhcpSnooping(40),
--        hsrp(41),
--        svi(42),
--        vmm(43),
--        pvlan(44),
--        tunnelManager(45),
--        ethPortSec(46),
--        lisp(47),
--        trustSec(48),
--        copp(49),
--        udld(50),
--        mcecm(51),
--        pbr(52),
--        nfm(53),
--        isapi(54),
--        vrrp(55),
--        netSift(56),
--        isisL2(57),
--        cimServer(58),
--        otv(59),
--        sanTap(60),
--        nasb(61),
--        dmm(62),
--        u2rib(63),
--        isisOtv(64),
--        orib(65),
--        fcoe(66),
--        siaServiceBroker(67),
--        evfp(68),
--        vtp(69),
--        splitter(70),
--        sfm(71),
--        ioa(72),
--        telnetServer(73),
--        sshServer(74),
--        httpServer(75),
--        wccp(76),
--        siaSve(77),
--        xcvrFreq(78),
--        assocMgr(79),
--        lldp(80),
--        rsvp(81),
--        ldp(82),
--        te(83),
--        mplsOam(84),
--        l2vpn(85),
--        drap(86),
--        bfd(87),
--        bfdApp(88),
--        fex(89),
--        pong(90),
--        rtp(91),
--        ldap(92),
--        privilege(93),
--        oim(94),
--        mplsMgr(95),
--        ulib(96),
--        scp(97),
--        sftp(98),
--        l3vpn(99),
--        mvpn(101),
--        ipPool(102),
--        uufb(103),
--        umfb(104),
--        ethernetNpv(105),
--        wccpClient(106),
--        scadaGw(107),
--        poe(108),
--        flexlink(109),
--        niv(110),
--        vem(111),
--        ewise(112),
--        onep(113),
--        slaS(114),
--        slaR(115),
--        rise(116),
--        pppManager(117),
--        itronMcastAgent(118),
--        vsmAggregation(119),
--        segmentation(120),
--        vrrpv3(121),
--        vTracker(122),
--        fdmi(123),
--        cmm(124),
--        ntp(125),
--        fabricAccess(126),
--        nat(127),
--        vlanVnSeg(128),
--        bulkStat(129),
--        bbu(130),
--        vnSegment(131),
--        evb(132),
--        ngMvpn(134),
--        hmm(135),
--        vxlan(136),
--        mvrp(137),
--        evmed(138),
--        nSegMgr(139),
--        vff(140),
--        sol(141),
--        mplsStatic(142),
--        nxapi(143),
--        itd(144),
--        vmTracker(145),
--        poap(200)
--        }
    ACCESS not-accessible
    STATUS deprecated
    DESCRIPTION
        "A unique index representing the feature in this entry.
        cfcFeatureCtrlIndex object is superseded by 
        cfcFeatureCtrlIndex2."
    ::= { cfcFeatureCtrlEntry 1 }

cfcFeatureCtrlName OBJECT-TYPE
    SYNTAX SnmpAdminString(SIZE(1..32))
--    Rsyntax OCTET STRING(SIZE(1..32))
    ACCESS read-only
    STATUS deprecated
    DESCRIPTION
        "A human readable unique string representing the name of
        this feature.
        cfcFeatureCtrlName object is superseded by 
        cfcFeatureCtrlName2."
    ::= { cfcFeatureCtrlEntry 2 }

cfcFeatureCtrlAction OBJECT-TYPE
    SYNTAX CiscoFeatureAction
--    Rsyntax INTEGER {
--        noOp(1),
--        enable(2),
--        disable(3),
--        install(4),
--        uninstall(5),
--        allow(6),
--        disallow(7)
--        }
    ACCESS read-write
    STATUS deprecated
    DESCRIPTION
        "The action to be triggered for the feature. Setting the
        value of this object to  a value other than 'enable' or 
        'disable'  does not trigger any action for the feature
        and hence does not affect the value of corresponding
        instance of 'cfcFeatureCtrlLastAction'. Retrieving the
        value of this object via SNMP will always return 'noOp'.
        cfcFeatureCtrlAction object is superseded by 
        cfcFeatureCtrlAction2."
    ::= { cfcFeatureCtrlEntry 3 }

cfcFeatureCtrlLastAction OBJECT-TYPE
    SYNTAX CiscoFeatureAction
--    Rsyntax INTEGER {
--        noOp(1),
--        enable(2),
--        disable(3),
--        install(4),
--        uninstall(5),
--        allow(6),
--        disallow(7)
--        }
    ACCESS read-only
    STATUS deprecated
    DESCRIPTION
        "The last action triggered for the feature. If no action
        has been triggered for the feature since the last reboot
        of the sytem, then retrieving the value of this object 
        via SNMP will return 'noOp'.
        cfcFeatureCtrlLastAction object is superseded by
        cfcFeatureCtrlLastAction2."
    ::= { cfcFeatureCtrlEntry 4 }

cfcFeatureCtrlLastActionResult OBJECT-TYPE
    SYNTAX CiscoFeatureActionResult
--    Rsyntax INTEGER {
--        none(1),
--        actionSuccess(2),
--        actionFailed(3),
--        actionInProgress(4)
--        }
    ACCESS read-only
    STATUS deprecated
    DESCRIPTION
        "The result of execution of last action (represented by
        value of 'cfcFeatureCtrlLastAction') for the feature. When 
        the value of this object is 'actionInProgress', the value
        of the corresponding instance of 'cfcFeatureCtrlAction' 
        can not be modified.
        cfcFeatureCtrlLastActionResult object is superseded by
        cfcFeatureCtrlLastActionResult2."
    ::= { cfcFeatureCtrlEntry 5 }

cfcFeatureCtrlLastFailureReason OBJECT-TYPE
    SYNTAX SnmpAdminString
--    Rsyntax OCTET STRING(SIZE(0..255))
    ACCESS read-only
    STATUS deprecated
    DESCRIPTION
        "The failure reason description for the failed execution
        of last action triggered for the feature. 
        If the corresponding instance of 
        'cfcFeatureCtrlLastActionResult' has the value
        'actionFailed', then this object contains the reason
         as to why it failed.  Otherwise, the value of this
         object is the zero-length string.
        cfcFeatureCtrlLastFailureReason object is superseded by
        cfcFeatureCtrlLastFailureReason2."
    ::= { cfcFeatureCtrlEntry 6 }

cfcFeatureCtrlOpStatus OBJECT-TYPE
    SYNTAX CiscoFeatureStatus
--    Rsyntax INTEGER {
--        unknown(1),
--        enabled(2),
--        disabled(3),
--        installed(4),
--        uninstalled(5)
--        }
    ACCESS read-only
    STATUS deprecated
    DESCRIPTION
        "The current operating status of the feature.
        cfcFeatureCtrlOpStatus object is superseded by
        cfcFeatureCtrlOpStatus2."
    ::= { cfcFeatureCtrlEntry 7 }

cfcFeatureCtrlOpStatusReason OBJECT-TYPE
    SYNTAX SnmpAdminString
--    Rsyntax OCTET STRING(SIZE(0..255))
    ACCESS read-only
    STATUS deprecated
    DESCRIPTION
        "The reason description for the current operating status
        (represented by the  value of corresponding instance of
        'cfcFeatureCtrlOpStatus') of the feature.
        The reason for the current operating status of the feature
        could be other than explicit user triggered action on the 
        feature.
        cfcFeatureCtrlOpStatusReason object is superseded by
        cfcFeatureCtrlOpStatusReason2."
    ::= { cfcFeatureCtrlEntry 8 }

cfcFeatureCtrl2Table OBJECT-TYPE
    SYNTAX SEQUENCE OF CfcFeatureCtrl2Entry
    ACCESS not-accessible
    STATUS mandatory
    DESCRIPTION
        "A table consisting of entries for all the features that can
        be optionally enabled/disabled in the system. This table 
        provides administrative control and current operating state
        information of the feature. This table deprecates 
        cfcFeatureCtrlTable"
    ::= { cfcFeature 2 }

cfcFeatureCtrl2Entry OBJECT-TYPE
    SYNTAX CfcFeatureCtrl2Entry
    ACCESS not-accessible
    STATUS mandatory
    DESCRIPTION
        "An entry (conceptual row) in the 'cfcFeatureCtrl2Table'.
        Each row represents an optional feature in the system."
    INDEX { cfcFeatureCtrlIndex2, cfcFeatureCtrlInstanceNum2 }
    ::= { cfcFeatureCtrl2Table 1 }

CfcFeatureCtrl2Entry ::= SEQUENCE {
    cfcFeatureCtrlIndex2 CiscoOptionalFeature,
    cfcFeatureCtrlInstanceNum2 Gauge,
    cfcFeatureCtrlName2 SnmpAdminString,
    cfcFeatureCtrlAction2 CiscoFeatureAction,
    cfcFeatureCtrlLastAction2 CiscoFeatureAction,
    cfcFeatureCtrlLastActionResult2 CiscoFeatureActionResult,
    cfcFeatureCtrlLastFailureReason2 SnmpAdminString,
    cfcFeatureCtrlOpStatus2 CiscoFeatureStatus,
    cfcFeatureCtrlOpStatusReason2 SnmpAdminString,
    cfcFeatureCtrlTag2 SnmpAdminString
    }

cfcFeatureCtrlIndex2 OBJECT-TYPE
    SYNTAX CiscoOptionalFeature
--    Rsyntax INTEGER {
--        ivr(1),
--        fcip(2),
--        fcsp(3),
--        ficon(4),
--        iscsi(5),
--        tacacs(6),
--        qosManager(7),
--        portSecurity(8),
--        fabricBinding(9),
--        iscsiInterfaceVsanMembership(10),
--        ike(11),
--        isns(12),
--        ipSec(13),
--        portTracker(14),
--        scheduler(15),
--        npiv(16),
--        sanExtTuner(17),
--        dpvm(18),
--        extenedCredit(19),
--        cloudDiscovery(20),
--        isis(21),
--        ospf(22),
--        ospfV3(23),
--        rip(24),
--        bgp(25),
--        pim(26),
--        igmp(27),
--        msdp(28),
--        pim6(29),
--        eigrp(30),
--        sdv(31),
--        cluster(32),
--        sme(33),
--        lacp(34),
--        amt(35),
--        dot1x(36),
--        npv(37),
--        l2nac(38),
--        glbp(39),
--        dhcpSnooping(40),
--        hsrp(41),
--        svi(42),
--        vmm(43),
--        pvlan(44),
--        tunnelManager(45),
--        ethPortSec(46),
--        lisp(47),
--        trustSec(48),
--        copp(49),
--        udld(50),
--        mcecm(51),
--        pbr(52),
--        nfm(53),
--        isapi(54),
--        vrrp(55),
--        netSift(56),
--        isisL2(57),
--        cimServer(58),
--        otv(59),
--        sanTap(60),
--        nasb(61),
--        dmm(62),
--        u2rib(63),
--        isisOtv(64),
--        orib(65),
--        fcoe(66),
--        siaServiceBroker(67),
--        evfp(68),
--        vtp(69),
--        splitter(70),
--        sfm(71),
--        ioa(72),
--        telnetServer(73),
--        sshServer(74),
--        httpServer(75),
--        wccp(76),
--        siaSve(77),
--        xcvrFreq(78),
--        assocMgr(79),
--        lldp(80),
--        rsvp(81),
--        ldp(82),
--        te(83),
--        mplsOam(84),
--        l2vpn(85),
--        drap(86),
--        bfd(87),
--        bfdApp(88),
--        fex(89),
--        pong(90),
--        rtp(91),
--        ldap(92),
--        privilege(93),
--        oim(94),
--        mplsMgr(95),
--        ulib(96),
--        scp(97),
--        sftp(98),
--        l3vpn(99),
--        mvpn(101),
--        ipPool(102),
--        uufb(103),
--        umfb(104),
--        ethernetNpv(105),
--        wccpClient(106),
--        scadaGw(107),
--        poe(108),
--        flexlink(109),
--        niv(110),
--        vem(111),
--        ewise(112),
--        onep(113),
--        slaS(114),
--        slaR(115),
--        rise(116),
--        pppManager(117),
--        itronMcastAgent(118),
--        vsmAggregation(119),
--        segmentation(120),
--        vrrpv3(121),
--        vTracker(122),
--        fdmi(123),
--        cmm(124),
--        ntp(125),
--        fabricAccess(126),
--        nat(127),
--        vlanVnSeg(128),
--        bulkStat(129),
--        bbu(130),
--        vnSegment(131),
--        evb(132),
--        ngMvpn(134),
--        hmm(135),
--        vxlan(136),
--        mvrp(137),
--        evmed(138),
--        nSegMgr(139),
--        vff(140),
--        sol(141),
--        mplsStatic(142),
--        nxapi(143),
--        itd(144),
--        vmTracker(145),
--        poap(200)
--        }
    ACCESS not-accessible
    STATUS mandatory
    DESCRIPTION
        "A unique index representing the base feature id in this
        entry."
    ::= { cfcFeatureCtrl2Entry 1 }

cfcFeatureCtrlInstanceNum2 OBJECT-TYPE
    SYNTAX Gauge
    ACCESS not-accessible
    STATUS mandatory
    DESCRIPTION
        "An index representing the feature instance number in this
        entry."
    ::= { cfcFeatureCtrl2Entry 2 }

cfcFeatureCtrlName2 OBJECT-TYPE
    SYNTAX SnmpAdminString(SIZE(1..32))
--    Rsyntax OCTET STRING(SIZE(1..32))
    ACCESS read-only
    STATUS mandatory
    DESCRIPTION
        "A human readable unique string representing the name of
        this feature."
    ::= { cfcFeatureCtrl2Entry 3 }

cfcFeatureCtrlAction2 OBJECT-TYPE
    SYNTAX CiscoFeatureAction
--    Rsyntax INTEGER {
--        noOp(1),
--        enable(2),
--        disable(3),
--        install(4),
--        uninstall(5),
--        allow(6),
--        disallow(7)
--        }
    ACCESS read-write
    STATUS mandatory
    DESCRIPTION
        "The action to be triggered for the feature. Setting the
        value of this object to  a value other than 'enable' or 
        'disable'  does not trigger any action for the feature
        and hence does not affect the value of corresponding
        instance of 'cfcFeatureCtrlLastAction2'. Retrieving the
        value of this object via SNMP will always return 'noOp'."
    ::= { cfcFeatureCtrl2Entry 4 }

cfcFeatureCtrlLastAction2 OBJECT-TYPE
    SYNTAX CiscoFeatureAction
--    Rsyntax INTEGER {
--        noOp(1),
--        enable(2),
--        disable(3),
--        install(4),
--        uninstall(5),
--        allow(6),
--        disallow(7)
--        }
    ACCESS read-only
    STATUS mandatory
    DESCRIPTION
        "The last action triggered for the feature. If no action
        has been triggered for the feature since the last reboot
        of the sytem, then retrieving the value of this object 
        via SNMP will return 'noOp'."
    ::= { cfcFeatureCtrl2Entry 5 }

cfcFeatureCtrlLastActionResult2 OBJECT-TYPE
    SYNTAX CiscoFeatureActionResult
--    Rsyntax INTEGER {
--        none(1),
--        actionSuccess(2),
--        actionFailed(3),
--        actionInProgress(4)
--        }
    ACCESS read-only
    STATUS mandatory
    DESCRIPTION
        "The result of execution of last action (represented by
        value of 'cfcFeatureCtrlLastAction2') for the feature. When 
        the value of this object is 'actionInProgress', the value
        of the corresponding instance of 'cfcFeatureCtrlAction2' 
        can not be modified."
    ::= { cfcFeatureCtrl2Entry 6 }

cfcFeatureCtrlLastFailureReason2 OBJECT-TYPE
    SYNTAX SnmpAdminString
--    Rsyntax OCTET STRING(SIZE(0..255))
    ACCESS read-only
    STATUS mandatory
    DESCRIPTION
        "The failure reason description for the failed execution
        of last action triggered for the feature. 
        If the corresponding instance of 
        'cfcFeatureCtrlLastActionResult2' has the value
        'actionFailed', then this object contains the reason
         as to why it failed.  Otherwise, the value of this
         object is the zero-length string."
    ::= { cfcFeatureCtrl2Entry 7 }

cfcFeatureCtrlOpStatus2 OBJECT-TYPE
    SYNTAX CiscoFeatureStatus
--    Rsyntax INTEGER {
--        unknown(1),
--        enabled(2),
--        disabled(3),
--        installed(4),
--        uninstalled(5)
--        }
    ACCESS read-only
    STATUS mandatory
    DESCRIPTION
        "The current operating status of the feature."
    ::= { cfcFeatureCtrl2Entry 8 }

cfcFeatureCtrlOpStatusReason2 OBJECT-TYPE
    SYNTAX SnmpAdminString
--    Rsyntax OCTET STRING(SIZE(0..255))
    ACCESS read-only
    STATUS mandatory
    DESCRIPTION
        "The reason description for the current operating status
        (represented by the  value of corresponding instance of
        'cfcFeatureCtrlOpStatus2') of the feature.
        The reason for the current operating status of the feature
        could be other than explicit user triggered action on the 
        feature."
    ::= { cfcFeatureCtrl2Entry 9 }

cfcFeatureCtrlTag2 OBJECT-TYPE
    SYNTAX SnmpAdminString(SIZE(0..32))
--    Rsyntax OCTET STRING(SIZE(0..32))
    ACCESS read-write
    STATUS mandatory
    DESCRIPTION
        "A human readable unique string identifying a given instance of
        a multiple instance feature."
    ::= { cfcFeatureCtrl2Entry 10 }

cfcFeatureSetTable OBJECT-TYPE
    SYNTAX SEQUENCE OF CfcFeatureSetEntry
    ACCESS not-accessible
    STATUS mandatory
    DESCRIPTION
        "This table lists all of feature sets that are supported
        by the system.  The number of feature sets supported is 
        determined by the system.  The system creates a row in
        the cfcFeatureSetTable when it detects a feature set
        that supports the type of global control described by
        this MIB module."
    ::= { cfcFeature 3 }

cfcFeatureSetEntry OBJECT-TYPE
    SYNTAX CfcFeatureSetEntry
    ACCESS not-accessible
    STATUS mandatory
    DESCRIPTION
        "An entry containing management information for a feature set."
    INDEX { cfcFeatureSetIndex }
    ::= { cfcFeatureSetTable 1 }

CfcFeatureSetEntry ::= SEQUENCE {
    cfcFeatureSetIndex CiscoOptionalFeatureSet,
    cfcFeatureSetName SnmpAdminString,
    cfcFeatureSetAction CiscoFeatureAction,
    cfcFeatureSetLastAction CiscoFeatureAction,
    cfcFeatureSetLastActionResult CiscoFeatureActionResult,
    cfcFeatureSetLastFailureReason SnmpAdminString,
    cfcFeatureSetOpStatus CiscoFeatureStatus,
    cfcFeatureSetOpStatusReason SnmpAdminString
    }

cfcFeatureSetIndex OBJECT-TYPE
    SYNTAX CiscoOptionalFeatureSet
--    Rsyntax INTEGER {
--        fcoe(1),
--        l2mp(2),
--        fex(3),
--        mpls(4),
--        fabric(7)
--        }
    ACCESS not-accessible
    STATUS mandatory
    DESCRIPTION
        "A unique index representing the feature set in this entry."
    ::= { cfcFeatureSetEntry 1 }

cfcFeatureSetName OBJECT-TYPE
    SYNTAX SnmpAdminString
--    Rsyntax OCTET STRING(SIZE(0..255))
    ACCESS read-only
    STATUS mandatory
    DESCRIPTION
        "This object indicates the name of a feature set such as fcoe
        and fex."
    ::= { cfcFeatureSetEntry 2 }

cfcFeatureSetAction OBJECT-TYPE
    SYNTAX CiscoFeatureAction
--    Rsyntax INTEGER {
--        noOp(1),
--        enable(2),
--        disable(3),
--        install(4),
--        uninstall(5),
--        allow(6),
--        disallow(7)
--        }
    ACCESS read-write
    STATUS mandatory
    DESCRIPTION
        "This object specifies an action for the system to
        execute against the corresponding feature set."
    ::= { cfcFeatureSetEntry 3 }

cfcFeatureSetLastAction OBJECT-TYPE
    SYNTAX CiscoFeatureAction
--    Rsyntax INTEGER {
--        noOp(1),
--        enable(2),
--        disable(3),
--        install(4),
--        uninstall(5),
--        allow(6),
--        disallow(7)
--        }
    ACCESS read-only
    STATUS mandatory
    DESCRIPTION
        "This object indicates the last action triggered for the
        feature set. If no action has been triggered for the feature 
        set since the last reboot of the sytem, then retrieving the 
        value of this object via SNMP will return 'noOp'."
    ::= { cfcFeatureSetEntry 4 }

cfcFeatureSetLastActionResult OBJECT-TYPE
    SYNTAX CiscoFeatureActionResult
--    Rsyntax INTEGER {
--        none(1),
--        actionSuccess(2),
--        actionFailed(3),
--        actionInProgress(4)
--        }
    ACCESS read-only
    STATUS mandatory
    DESCRIPTION
        "This object indicates the result of the last action
        that was applied to the feature set."
    ::= { cfcFeatureSetEntry 5 }

cfcFeatureSetLastFailureReason OBJECT-TYPE
    SYNTAX SnmpAdminString
--    Rsyntax OCTET STRING(SIZE(0..255))
    ACCESS read-only
    STATUS mandatory
    DESCRIPTION
        "This object indicates the failure code of the
        last action that was applied to the feature set."
    ::= { cfcFeatureSetEntry 6 }

cfcFeatureSetOpStatus OBJECT-TYPE
    SYNTAX CiscoFeatureStatus
--    Rsyntax INTEGER {
--        unknown(1),
--        enabled(2),
--        disabled(3),
--        installed(4),
--        uninstalled(5)
--        }
    ACCESS read-only
    STATUS mandatory
    DESCRIPTION
        "This object indicates the current status of the feature set."
    ::= { cfcFeatureSetEntry 7 }

cfcFeatureSetOpStatusReason OBJECT-TYPE
    SYNTAX SnmpAdminString
--    Rsyntax OCTET STRING(SIZE(0..255))
    ACCESS read-only
    STATUS mandatory
    DESCRIPTION
        "This object indicates the reason of the current
        status of the feature set."
    ::= { cfcFeatureSetEntry 8 }

cfcFeatureSetNotifEnable OBJECT-TYPE
    SYNTAX TruthValue
--    Rsyntax INTEGER {
--        true(1),
--        false(2)
--        }
    ACCESS read-write
    STATUS mandatory
    DESCRIPTION
        "This object specifies whether a notification is generated
        when a feature set status changes."
    DEFVAL { false }
    ::= { cfcNotifControl 1 }

ciscoFeatureOpStatusChange TRAP-TYPE
-- Reverse mappable trap
    ENTERPRISE ciscoFeatureCtrlMIB
    VARIABLES {
        cfcFeatureCtrlOpStatus }
--  Status
--    deprecated
    DESCRIPTION
        "Notification to indicate that the operational state of
        this feature has changed. The 'cfcFeatureCtrlOpStatus'
        indicates the new state of the feature. 
        ciscoFeatureOpStatusChange object is superseded by
        ciscoFeatOpStatusChange."
    ::= 1

ciscoFeatOpStatusChange TRAP-TYPE
-- Reverse mappable trap
    ENTERPRISE ciscoFeatureCtrlMIB
    VARIABLES {
        cfcFeatureCtrlOpStatus2 }
--  Status
--    mandatory
    DESCRIPTION
        "Notification to indicate that the operational state of
        this feature has changed. The 'cfcFeatureCtrlOpStatus2'
        indicates the new state of the feature. This notification
        deprecates ciscoFeatureOpStatusChange."
    ::= 2

ciscoFeatureSetOpStatusChange TRAP-TYPE
-- Reverse mappable trap
    ENTERPRISE ciscoFeatureCtrlMIB
    VARIABLES {
        cfcFeatureSetOpStatus }
--  Status
--    mandatory
    DESCRIPTION
        "This notification indicates that the state of
        this feature set has changed. The 'cfcFeatureSetOpStatus'
        indicates the new state of the feature set."
    ::= 3

cfcFeatureGroup OBJECT IDENTIFIER ::= { ciscoFeatureCtrlMIBGroups 1 }
-- OBJECT-GROUP
--  Status
--    deprecated
--  Descr
--    A collection of objects for controlling the features in
--    the system.
--    cfcFeatureGroup object is superseded by cfcFeatureGroupRev.
--  objects
--    cfcFeatureCtrlName, cfcFeatureCtrlAction, 
--    cfcFeatureCtrlLastAction, cfcFeatureCtrlLastActionResult, 
--    cfcFeatureCtrlLastFailureReason, cfcFeatureCtrlOpStatus, 
--    cfcFeatureCtrlOpStatusReason

cfcFeatureGroupRev OBJECT IDENTIFIER ::= { ciscoFeatureCtrlMIBGroups 3 }
-- OBJECT-GROUP
--  Status
--    mandatory
--  Descr
--    A collection of objects for controlling the features in
--    the system. This group deprecates cfcFeatureGroup.
--  objects
--    cfcFeatureCtrlName2, cfcFeatureCtrlTag2, 
--    cfcFeatureCtrlAction2, cfcFeatureCtrlLastAction2, 
--    cfcFeatureCtrlLastActionResult2, 
--    cfcFeatureCtrlLastFailureReason2, cfcFeatureCtrlOpStatus2, 
--    cfcFeatureCtrlOpStatusReason2

cfcFeatureSetGroup OBJECT IDENTIFIER ::= { ciscoFeatureCtrlMIBGroups 5 }
-- OBJECT-GROUP
--  Status
--    mandatory
--  Descr
--    A collection of objects for controlling a feature set
--    in the system.
--  objects
--    cfcFeatureSetName, cfcFeatureSetAction, 
--    cfcFeatureSetLastAction, cfcFeatureSetLastActionResult, 
--    cfcFeatureSetLastFailureReason, cfcFeatureSetOpStatus, 
--    cfcFeatureSetOpStatusReason

cfcFeatureSetNotificationCtrlGroup OBJECT IDENTIFIER ::= { ciscoFeatureCtrlMIBGroups 6 }
-- OBJECT-GROUP
--  Status
--    mandatory
--  Descr
--    This group of objects controls the sending of
--    notifications defined in this MIB module.
--  objects
--    cfcFeatureSetNotifEnable

cfcNotificationGroup OBJECT IDENTIFIER ::= { ciscoFeatureCtrlMIBGroups 2 }
-- NOTIFICATION-GROUP
--  Status
--    deprecated
--  Descr
--    A collection of notifications to monitor state of the
--    features.
--    cfcNotificationGroup object is superseded 
--    by cfcNotificationGroupRev.
--  notifications
--    ciscoFeatureOpStatusChange

cfcNotificationGroupRev OBJECT IDENTIFIER ::= { ciscoFeatureCtrlMIBGroups 4 }
-- NOTIFICATION-GROUP
--  Status
--    mandatory
--  Descr
--    A collection of notifications to monitor state of the
--    features.
--  notifications
--    ciscoFeatOpStatusChange

cfcFeatureSetNotificationGroup OBJECT IDENTIFIER ::= { ciscoFeatureCtrlMIBGroups 7 }
-- NOTIFICATION-GROUP
--  Status
--    mandatory
--  Descr
--    A collection of notifications to monitor state of a
--    feature set.
--  notifications
--    ciscoFeatureSetOpStatusChange

ciscoFeatureCtrlMIBCompliance OBJECT IDENTIFIER ::= { ciscoFeatureCtrlMIBCompliances 1 }
-- MODULE-COMPLIANCE
--  Status
--    deprecated
--  Descr
--    The compliance statement for entities which implement the
--    CISCO-FEATURE-CONTROL-MIB.
--  Module
--    >>current<<
--   MandGroup
--    cfcFeatureGroup
--   MandGroup
--    cfcNotificationGroup

ciscoFeatureCtrlMIBComplianceRev OBJECT IDENTIFIER ::= { ciscoFeatureCtrlMIBCompliances 2 }
-- MODULE-COMPLIANCE
--  Status
--    deprecated
--  Descr
--    The compliance statement for entities which implement the
--    CISCO-FEATURE-CONTROL-MIB. This compliance deprecates
--    ciscoFeatureCtrlMIBCompliance.
--  Module
--    >>current<<
--   MandGroup
--    cfcFeatureGroupRev
--   MandGroup
--    cfcNotificationGroupRev

ciscoFeatureSetCtrlMIBComplianceRev1 OBJECT IDENTIFIER ::= { ciscoFeatureCtrlMIBCompliances 3 }
-- MODULE-COMPLIANCE
--  Status
--    mandatory
--  Descr
--    The compliance statement for entities which implement
--    the CISCO-FEATURE-CONTROL-MIB.
--  Module
--    >>current<<
--   MandGroup
--    cfcFeatureSetGroup
--   MandGroup
--    cfcFeatureSetNotificationCtrlGroup
--   MandGroup
--    cfcFeatureSetNotificationGroup
--   MandGroup
--    cfcFeatureGroupRev
--   MandGroup
--    cfcNotificationGroupRev


END
