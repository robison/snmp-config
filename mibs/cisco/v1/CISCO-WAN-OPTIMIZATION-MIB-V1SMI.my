-- MIB file created 23-May-2013 11:42:40, by
--   SMICng version 2.2.11-beta(PRO)(Solaris), January 20, 2001. Enterprise key cisco.com

CISCO-WAN-OPTIMIZATION-MIB DEFINITIONS ::= BEGIN

-- From file: "CISCO-WAN-OPTIMIZATION-MIB.my"
-- Compile options "4 7 F H N W 03 06 0B 0G 0N 0T"

IMPORTS
    TruthValue, TimeInterval, DateAndTime, TimeStamp
            FROM SNMPv2-TC-v1
    CounterBasedGauge64
            FROM HCNUM-TC
    SnmpAdminString
            FROM SNMP-FRAMEWORK-MIB
    CiscoMilliSeconds, TimeIntervalSec, Unsigned64
            FROM CISCO-TC
    cpmCPUTotalMonIntervalValue
            FROM CISCO-PROCESS-MIB
    ciscoMgmt
            FROM CISCO-SMI
    Counter, Gauge
            FROM RFC1155-SMI
    OBJECT-TYPE
            FROM RFC-1212
    TRAP-TYPE
            FROM RFC-1215;

ciscoWanOptimizationMIB OBJECT IDENTIFIER ::= { ciscoMgmt 762 }
-- MODULE-IDENTITY
--  LastUpdated
--    201305230000Z
--  OrgName
--    Cisco Systems, Inc.
--  ContactInfo
--    Cisco Systems
--    Customer Service
--    Postal: 170 W Tasman Drive
--    San Jose, CA  95134
--    USA
--    
--    Tel: +1 800 553-NETS
--    E-mail: cs-waas@cisco.com, cs-waas-express@cisco.com
--  Descr
--    This MIB is for managing Wide Area Network (WAN) Optimization
--    systems. The objective of WAN optimization system is to reduce
--    as much traffic as possible on WAN link and improve the
--    application response time for various applications, which gets
--    affected due to bandwidth, packet loss, congestion and latency
--    limitations of WAN link. WAN optimization system is generally
--    peer based system. They are located at both end of WAN link and
--    peer with each other to perform optimization. This MIB provides
--    instrumentation for monitoring statistics for various features
--    implemented for WAN optimization. WAN optimization features
--    includes TCP protocol optimizations and various Application
--    Optimizers (AOs). AOs include SMB AO, HTTP AO, CIFS AO, NFS AO,
--    MAPI AO, VIDEO AO, SSL AO and EPM AO.
--    
--    Acronyms and Terminology used in this MIB are:
--    AO               : Application Optimizer
--    TFO              : Traffic Flow Optimization
--    SMB              : Server Message Block
--    CIFS             : Common Internet File System
--    HTTP             : Hyper Text Transfer Protocol
--    NFS              : Network File System
--    SSL              : Secure Socket Layer
--    MAPI             : Messaging Application Programming Interface
--    EPM              : End Point Mapper
--    RA               : Read Ahead
--    MD               : Meta Data
--    PT               : Pass Through
--    AD               : Auto Discovery
--    RTT              : Round Trip Time
--    Conn             : Connections
--    File Server      : SMB/CIFS file server
--    peer             : It refers to peer WAN optimization system 
--                       located on other end of WAN and registered 
--                       with this device to optimize the traffic.
--    SharePoint       : SharePoint is a Microsoft Application that 
--                       provides a collaborative environment for 
--                       using Microsoft Office and related 
--                       applications. Typical deployments of 
--                       Microsoft SharePoint use one or more        
--                       SharePoint servers in a server farm for 
--                       scalability. The actual data for the various
--                       documents, etc. are usually stored in a 
--                       backend database. The SharePoint server(s) 
--                       communicate with the backend database using 
--                       SharePoint Back-end protocols. Clients 
--                       (either Microsoft Office Applications like 
--                       Word, Excel, PowerPoint or Web Browsers) 
--                       typically connect to the SharePoint server 
--                       and communicate using SOAP over HTTP.
--    Fast Connections : End to end connections which uses existing 
--                       TCP connection over WAN and reconstructs
--                       only LAN connection is fast connection.
--    DRE              : Data Redundancy Elimination.
--    LZ               : Lemple-Ziv data compression.
--  RevDate
--    201305230000Z
--  RevDescr
--    Added the below counters in cwoAoSmbxStats table Signed SMB
--    Bytes Stats enhancement feature
--    cwoAoSmbxStatsRdL4SignWANBytes
--    cwoAoSmbxStatsWrL4SignWANBytes
--    cwoAoSmbxStatsRdSignLANBytes
--    cwoAoSmbxStatsWrSignLANBytes
--  RevDate
--    201212130000Z
--  RevDescr
--    Added the below new counters which display SharePoint AO
--    statistics in cwoAoHttpxStats group.
--    cwoAoHttpxStatsTotalSPSessions
--    cwoAoHttpxStatsTotalSPPFSessions
--    cwoAoHttpxStatsTotalSPPFObjects
--    cwoAoHttpxStatsTotalSPRTTSaved
--    cwoAoHttpxStatsTotalSPPFMissTime
--    
--    Added the below new counters in cwoAoCifsxStats group to support
--    the CIFS Atkins feature.
--    cwoAoCifsxStatsFFTotalReqs
--    cwoAoCifsxStatsFFRemoteReqs
--    cwoAoCifsxStatsFFLocalRespTime
--    cwoAoCifsxStatsFFRemoteRespTime
--    cwoAoCifsxStatsDirResources
--  RevDate
--    201203050000Z
--  RevDescr
--    (1) Added cwoAoStatsLoadStatus and cwoAoStatsBwOpt in
--    cwoAoStatsTable
--    (2) Added cwoAoSmbStatsBwOpt in cwoAoSmbxstats Group
--    (3) Added cwoAoHttpxStats - Statistics Group for HTTP AO
--    (4) Added cwoAoMapixStats - Statistics Group for MAPI AO
--    (5) Added cwoAoNfsxStats - Statistics Group for NFS AO
--    (6) Added cwoAoVideoxStats - Statistics Group for Video AO
--    (7) Added cwoAoCifsxstats - Statistics Group for CIFS AO
--    (8) Added cwoApp - Gorup which includes objects for
--    Applications associated with AOs.
--    (9) Added cwoPmap - Group which includes objects for 
--         policy-map.
--    (10) Added cwoCmap - Group which includes objects for 
--     class-maps associated with active policy-map.
--    (11) Addes cwoTfoStatsLoadStatus in cswTfoStats group
--  RevDate
--    201104190000Z
--  RevDescr
--    New License Notification Group has been added.
--  RevDate
--    201010260000Z
--  RevDescr
--    Initial version of this MIB.

ciscoWanOptimizationMIBNotifs OBJECT IDENTIFIER ::= { ciscoWanOptimizationMIB 0 }
ciscoWanOptimizationMIBObjects OBJECT IDENTIFIER ::= { ciscoWanOptimizationMIB 1 }
ciscoWanOptimizationMIBConform OBJECT IDENTIFIER ::= { ciscoWanOptimizationMIB 3 }
ciscoWanOptimizationMIBCompliances OBJECT IDENTIFIER ::= { ciscoWanOptimizationMIBConform 1 }
cwoGeneral      OBJECT IDENTIFIER ::= { ciscoWanOptimizationMIBObjects 1 }
cwoTfo          OBJECT IDENTIFIER ::= { ciscoWanOptimizationMIBObjects 2 }
cwoAo           OBJECT IDENTIFIER ::= { ciscoWanOptimizationMIBObjects 3 }
cwoApp          OBJECT IDENTIFIER ::= { ciscoWanOptimizationMIBObjects 4 }
cwoPmap         OBJECT IDENTIFIER ::= { ciscoWanOptimizationMIBObjects 5 }
cwoCmap         OBJECT IDENTIFIER ::= { ciscoWanOptimizationMIBObjects 6 }
cwoTfoStats     OBJECT IDENTIFIER ::= { cwoTfo 1 }
cwoAoSmbxStats  OBJECT IDENTIFIER ::= { cwoAo 2 }
cwoAoHttpxStats OBJECT IDENTIFIER ::= { cwoAo 3 }
cwoAoMapixStats OBJECT IDENTIFIER ::= { cwoAo 4 }
cwoAoNfsxStats  OBJECT IDENTIFIER ::= { cwoAo 5 }
cwoAoVideoxStats OBJECT IDENTIFIER ::= { cwoAo 6 }
cwoAoCifsxStats OBJECT IDENTIFIER ::= { cwoAo 7 }
ciscoWanOptimizationMIBGroups OBJECT IDENTIFIER ::= { ciscoWanOptimizationMIBConform 2 }

CwoAoName ::= OCTET STRING(SIZE(1..96))
-- TEXTUAL-CONVENTION
--  Status
--    mandatory
--  Descr
--    Represents the name of an Application Optimizer supported by
--    this system.

CwoAoOperationalState ::= INTEGER {
        shutdown(1),
        initializing(2),
        normalRunning(3),
        normalDisabled(4),
        licenseExpired(5),
        cleaningup(6),
        error(7)
        }
-- TEXTUAL-CONVENTION
--  Status
--    mandatory
--  Descr
--    Represents Various operational states of an Application
--    Optimizer.
--    
--    shutdown       : This state indicates that an AO is in shutdown
--                     state.
--    
--    initializing   : This state indicates that an AO is getting    
--                     Initialized.
--    
--    normalRunning  : This state indicates that an AO is running    
--                     normally.
--    
--    normalDisabled : This state indicates that an AO is in normal 
--                     disabled.
--    
--    licenseExpired : This state indicates that license for an AO is
--                     expired.
--    
--    cleaningup     : This state indicates that an AO is in cleaning
--                     up state.
--    
--    error          : This state indicates that some error has  
--                     happened in AO operation.

CwoLoadStates ::= INTEGER {
        unknown(1),
        green(2),
        yellow(3),
        red(4)
        }
-- TEXTUAL-CONVENTION
--  Status
--    mandatory
--  Descr
--    Represents load status of the system or feature.
--    
--    unknown    : This state is applicable when feature is not
--                 active or disabled.
--    green      : This state indicates that the feature is operating 
--                 normally, within acceptable load limits.  
--    yellow     : This state indicates that the feature is       
--                 overloaded, and new connections received by it
--                 may not get optimized.
--    red        : This state indicates that the feature is not    
--                 healthy, and existing as well as new
--                 connections received by it may not get optimized.

CwoTypes ::= INTEGER {
        waas(1),
        appnav(2)
        }
-- TEXTUAL-CONVENTION
--  Status
--    mandatory
--  Descr
--    Represents various types related to wan optimization system.
--    One such use is types of class-map and policy-map for wan
--    optimization syatem.
--    
--    waas           : It is used for wan optimization functionality.
--    appnav         : It is used for application traffic redirection 
--                     to wan optimization systems.

cwoGeneralActivePeers OBJECT-TYPE
    SYNTAX Gauge
--  Units
--    number of peers
    ACCESS read-only
    STATUS mandatory
    DESCRIPTION
        "This object contains total number of active peers connected
        with this device for WAN optimization."
    ::= { cwoGeneral 1 }

cwoGeneralMaxActivePeers OBJECT-TYPE
    SYNTAX Gauge
    ACCESS read-only
    STATUS mandatory
    DESCRIPTION
        "This object contains maximum number of peers that this device
        can peer with for WAN optimization."
    ::= { cwoGeneral 2 }

cwoGeneralCpuThrottleHigh OBJECT-TYPE
    SYNTAX Gauge(1..100)
--  Units
--    percent
    ACCESS read-write
    STATUS mandatory
    DESCRIPTION
        "This object contains high threshold (percentage) value of CPU
        usage of system when WAN optimization feature is running. The
        current CPU utilization, stored in cpmCPUTotalMonIntervalValue,
        is compared against this value. A cwoCpuThrottlingOn
        notification is generated whenever cpmCPUTotalMonIntervalValue
        exceeds cwoGeneralCpuThrottleHigh for
        cwoGeneralCpuThrottlPeriod."
    ::= { cwoGeneral 3 }

cwoGeneralCpuThrottleLow OBJECT-TYPE
    SYNTAX Gauge(1..100)
--  Units
--    percent
    ACCESS read-write
    STATUS mandatory
    DESCRIPTION
        "This object contains low threshold (percentage) value of CPU
        usage of system when WAN optimization feature is running. The 
        current CPU utilization, stored in cpmCPUTotalMonIntervalValue,
        is
        compared against this value. A cwoCpuThrottlingOff notification
        is generated if a prior cwoCpuThrottlingOn notification was 
        generated, and the current value of cpmCPUTotalMonIntervalValue
        is below cwoGeneralCpuThrottleLow for
        cwoGeneralCpuThrottlPeriod.
        
        Note that the value of cwoGeneralCpuThrottleLow must be less
        than
        or equal to cwoGeneralCpuThrottleHigh."
    ::= { cwoGeneral 4 }

cwoGeneralCpuThrottlPeriod OBJECT-TYPE
    SYNTAX TimeInterval
--    Rsyntax INTEGER(0..2147483647)
    ACCESS read-write
    STATUS mandatory
    DESCRIPTION
        "This Object indicates CPU throttling observation period. The
        value of the CPU utilization for this period is stored in 
        cpmCPUTotalMonIntervalValue. If the value of 
        cpmCPUTotalMonIntervalValue object is above  
        cwoGeneralCPUThrottleHigh, a cwoCPUThrottlingOn notification 
        is sent. If it is below cwoGeneralCPUThrottleLow, a 
        cwoCPUThrottlingOff notification is sent to the NMS."
    ::= { cwoGeneral 5 }

cwoTfoStatsTotalOptConn OBJECT-TYPE
    SYNTAX --?? syntax is not convertable to SMIv1
           Counter
    ACCESS read-only
    STATUS mandatory
    DESCRIPTION
        "This object contains total number of TCP connections optimized
        since TFO was started or its statistics were last reset."
    ::= { cwoTfoStats 1 }

cwoTfoStatsActiveOptConn OBJECT-TYPE
    SYNTAX --?? syntax is not convertable to SMIv1
           CounterBasedGauge64
--    Rsyntax Counter
    ACCESS read-only
    STATUS mandatory
    DESCRIPTION
        "This object contains number of currently active TCP connections
        getting optimized."
    ::= { cwoTfoStats 2 }

cwoTfoStatsMaxActiveConn OBJECT-TYPE
    SYNTAX --?? syntax is not convertable to SMIv1
           Unsigned64
--    Rsyntax Counter
    ACCESS read-only
    STATUS mandatory
    DESCRIPTION
        "This object contains maximum number of active TCP connections
        that this device can optimize."
    ::= { cwoTfoStats 3 }

cwoTfoStatsActiveOptTCPPlusConn OBJECT-TYPE
    SYNTAX --?? syntax is not convertable to SMIv1
           CounterBasedGauge64
--    Rsyntax Counter
    ACCESS read-only
    STATUS mandatory
    DESCRIPTION
        "This object contains number of active TCP connections going
        through TCP plus other optimization."
    ::= { cwoTfoStats 4 }

cwoTfoStatsActiveOptTCPOnlyConn OBJECT-TYPE
    SYNTAX --?? syntax is not convertable to SMIv1
           CounterBasedGauge64
--    Rsyntax Counter
    ACCESS read-only
    STATUS mandatory
    DESCRIPTION
        "This object contains number of active connections going through
        only TCP optimization."
    ::= { cwoTfoStats 5 }

cwoTfoStatsActiveOptTCPPrepConn OBJECT-TYPE
    SYNTAX --?? syntax is not convertable to SMIv1
           CounterBasedGauge64
--    Rsyntax Counter
    ACCESS read-only
    STATUS mandatory
    DESCRIPTION
        "This object contains number of current active TCP connections
        that were originated by an accelerator to acquire data in
        anticipation of its future use."
    ::= { cwoTfoStats 6 }

cwoTfoStatsActiveADConn OBJECT-TYPE
    SYNTAX --?? syntax is not convertable to SMIv1
           CounterBasedGauge64
--    Rsyntax Counter
    ACCESS read-only
    STATUS mandatory
    DESCRIPTION
        "This object contains number of current active TCP connections
        in the auto-discovery state."
    ::= { cwoTfoStats 7 }

cwoTfoStatsReservedConn OBJECT-TYPE
    SYNTAX --?? syntax is not convertable to SMIv1
           Unsigned64
--    Rsyntax Counter
    ACCESS read-only
    STATUS mandatory
    DESCRIPTION
        "This object contains number of TCP connections reserved for the
        MAPI accelerator."
    ::= { cwoTfoStats 8 }

cwoTfoStatsPendingConn OBJECT-TYPE
    SYNTAX --?? syntax is not convertable to SMIv1
           CounterBasedGauge64
--    Rsyntax Counter
    ACCESS read-only
    STATUS mandatory
    DESCRIPTION
        "This object contains number of TCP connections, which are
        pending in queue of connections to be optimized."
    ::= { cwoTfoStats 9 }

cwoTfoStatsActivePTConn OBJECT-TYPE
    SYNTAX --?? syntax is not convertable to SMIv1
           CounterBasedGauge64
--    Rsyntax Counter
    ACCESS read-only
    STATUS mandatory
    DESCRIPTION
        "This object contains number of active Pass Through TCP
        connections. Connections which are not selected for optimization
        are called Pass Through."
    ::= { cwoTfoStats 10 }

cwoTfoStatsTotalNormalClosedConn OBJECT-TYPE
    SYNTAX --?? syntax is not convertable to SMIv1
           Counter
    ACCESS read-only
    STATUS mandatory
    DESCRIPTION
        "This object contains total number of optimized TCP connections
        which were closed normally since TFO was started or its
        statistics were last reset."
    ::= { cwoTfoStats 11 }

cwoTfoStatsResetConn OBJECT-TYPE
    SYNTAX --?? syntax is not convertable to SMIv1
           Counter
    ACCESS read-only
    STATUS mandatory
    DESCRIPTION
        "This object contains total number of optimized TCP connections,
        which are reset since TFO was started or its statistics were
        last reset."
    ::= { cwoTfoStats 12 }

cwoTfoStatsLoadStatus OBJECT-TYPE
    SYNTAX CwoLoadStates
--    Rsyntax INTEGER {
--        unknown(1),
--        green(2),
--        yellow(3),
--        red(4)
--        }
    ACCESS read-only
    STATUS mandatory
    DESCRIPTION
        "This object indicates the load status of Traffic Flow Optimizer
        (TFO)."
    ::= { cwoTfoStats 13 }

cwoAoStatsTable OBJECT-TYPE
    SYNTAX SEQUENCE OF CwoAoStatsEntry
    ACCESS not-accessible
    STATUS mandatory
    DESCRIPTION
        "This table gives statistics of Application Optimizers."
    ::= { cwoAo 1 }

cwoAoStatsEntry OBJECT-TYPE
    SYNTAX CwoAoStatsEntry
    ACCESS not-accessible
    STATUS mandatory
    DESCRIPTION
        "An entry containing statistics for particular Application
        optimizer. An entry will be created during system startup and
        will include AOs, which are supported by this system."
    INDEX { cwoAoStatsName }
    ::= { cwoAoStatsTable 1 }

CwoAoStatsEntry ::= SEQUENCE {
    cwoAoStatsName CwoAoName,
    cwoAoStatsIsConfigured TruthValue,
    cwoAoStatsIsLicensed TruthValue,
    cwoAoStatsOperationalState CwoAoOperationalState,
    cwoAoStatsStartUpTime DateAndTime,
    cwoAoStatsLastResetTime DateAndTime,
    cwoAoStatsTotalHandledConns Counter,
    cwoAoStatsTotalOptConns Counter,
    cwoAoStatsTotalHandedOffConns Counter,
    cwoAoStatsTotalDroppedConns Counter,
    cwoAoStatsActiveOptConns Gauge,
    cwoAoStatsPendingConns Gauge,
    cwoAoStatsMaxActiveOptConns Gauge,
    cwoAoStatsLoadStatus CwoLoadStates,
    cwoAoStatsBwOpt Gauge
    }

cwoAoStatsName OBJECT-TYPE
    SYNTAX CwoAoName
--    Rsyntax OCTET STRING(SIZE(1..96))
    ACCESS not-accessible
    STATUS mandatory
    DESCRIPTION
        "This object represents name of the AO."
    ::= { cwoAoStatsEntry 1 }

cwoAoStatsIsConfigured OBJECT-TYPE
    SYNTAX TruthValue
--    Rsyntax INTEGER {
--        true(1),
--        false(2)
--        }
    ACCESS read-only
    STATUS mandatory
    DESCRIPTION
        "This object indicates whether the AO is configured or not. If
        AO is not configured then the operational state
        (cwoAoStatsOperationalState) of AO would be 'shutdown'."
    ::= { cwoAoStatsEntry 2 }

cwoAoStatsIsLicensed OBJECT-TYPE
    SYNTAX TruthValue
--    Rsyntax INTEGER {
--        true(1),
--        false(2)
--        }
    ACCESS read-only
    STATUS mandatory
    DESCRIPTION
        "This object indicates whether license for the AO is valid or
        not. If License for AO is not valid then operational state
        (cwoAoStatsOperationalState) of AO would be 'shutdown'."
    ::= { cwoAoStatsEntry 3 }

cwoAoStatsOperationalState OBJECT-TYPE
    SYNTAX CwoAoOperationalState
--    Rsyntax INTEGER {
--        shutdown(1),
--        initializing(2),
--        normalRunning(3),
--        normalDisabled(4),
--        licenseExpired(5),
--        cleaningup(6),
--        error(7)
--        }
    ACCESS read-only
    STATUS mandatory
    DESCRIPTION
        "This object indicates operational state of the AO. If AO is not
        configured or license is not valid for this AO then operational
        state of AO would be 'shutdown'."
    ::= { cwoAoStatsEntry 4 }

cwoAoStatsStartUpTime OBJECT-TYPE
    SYNTAX DateAndTime
--    Rsyntax OCTET STRING(SIZE(8|11))
    ACCESS read-only
    STATUS mandatory
    DESCRIPTION
        "This object contains date and time when AO was started. This
        object will hold NULL value when AO is in shutdown state."
    ::= { cwoAoStatsEntry 5 }

cwoAoStatsLastResetTime OBJECT-TYPE
    SYNTAX DateAndTime
--    Rsyntax OCTET STRING(SIZE(8|11))
    ACCESS read-only
    STATUS mandatory
    DESCRIPTION
        "This object contains date and time when statistics of AO were
        set to reset last time. When statistics of AO set to reset then
        all statistics counters will also set to reset. This object will
        hold NULL value when AO is in shutdown state."
    ::= { cwoAoStatsEntry 6 }

cwoAoStatsTotalHandledConns OBJECT-TYPE
    SYNTAX Counter
    ACCESS read-only
    STATUS mandatory
    DESCRIPTION
        "This object contains total number of connections handled by AO
        since it was started or its statistics were last reset."
    ::= { cwoAoStatsEntry 7 }

cwoAoStatsTotalOptConns OBJECT-TYPE
    SYNTAX Counter
    ACCESS read-only
    STATUS mandatory
    DESCRIPTION
        "This object contains total number of connections optimized by
        AO since it was started or its statistics were last reset."
    ::= { cwoAoStatsEntry 8 }

cwoAoStatsTotalHandedOffConns OBJECT-TYPE
    SYNTAX Counter
    ACCESS read-only
    STATUS mandatory
    DESCRIPTION
        "This object contains total number of connections handed off to
        Generic optimization by AO since it was started or its
        statistics last reset."
    ::= { cwoAoStatsEntry 9 }

cwoAoStatsTotalDroppedConns OBJECT-TYPE
    SYNTAX Counter
    ACCESS read-only
    STATUS mandatory
    DESCRIPTION
        "This object contains total number of connections dropped by AO
        since it was started or its statistics were last reset."
    ::= { cwoAoStatsEntry 10 }

cwoAoStatsActiveOptConns OBJECT-TYPE
    SYNTAX Gauge
    ACCESS read-only
    STATUS mandatory
    DESCRIPTION
        "This object contains number of active connections which are
        getting optimized by AO."
    ::= { cwoAoStatsEntry 11 }

cwoAoStatsPendingConns OBJECT-TYPE
    SYNTAX Gauge
    ACCESS read-only
    STATUS mandatory
    DESCRIPTION
        "This object contains number of connections currently pending in
        queue of connections to be optimized by AO."
    ::= { cwoAoStatsEntry 12 }

cwoAoStatsMaxActiveOptConns OBJECT-TYPE
    SYNTAX Gauge
    ACCESS read-only
    STATUS mandatory
    DESCRIPTION
        "This object contains maximum number of active TCP connections
        that AO can optimize."
    ::= { cwoAoStatsEntry 13 }

cwoAoStatsLoadStatus OBJECT-TYPE
    SYNTAX CwoLoadStates
--    Rsyntax INTEGER {
--        unknown(1),
--        green(2),
--        yellow(3),
--        red(4)
--        }
    ACCESS read-only
    STATUS mandatory
    DESCRIPTION
        "This object indicates the load status of an AO."
    ::= { cwoAoStatsEntry 14 }

cwoAoStatsBwOpt OBJECT-TYPE
    SYNTAX Gauge(0..100)
--  Units
--    percent
    ACCESS read-only
    STATUS mandatory
    DESCRIPTION
        "This object indicates the percentage bandwidth optimization
        achieved due to optimizations done by an AO."
    ::= { cwoAoStatsEntry 15 }

cwoAoSmbxStatsBytesReadCache OBJECT-TYPE
    SYNTAX --?? syntax is not convertable to SMIv1
           Counter
--  Units
--    bytes
    ACCESS read-only
    STATUS mandatory
    DESCRIPTION
        "This object contains total number of bytes read from SMB
        Application Optimizer cache (Read-ahead and Metadata cache)
        since it was started.
        
        Discontinuities in the value of this counter can occur at
        re-initialization of the SMB AO. The last discontinuity time is
        indicated by the value of cwoAoStatsLastResetTime for the SMB
        AO."
    ::= { cwoAoSmbxStats 1 }

cwoAoSmbxStatsBytesWriteCache OBJECT-TYPE
    SYNTAX --?? syntax is not convertable to SMIv1
           Counter
--  Units
--    bytes
    ACCESS read-only
    STATUS mandatory
    DESCRIPTION
        "This object contains total number of bytes written to SMB
        Application Optimizer cache (Read-ahead and Metadata) since it
        was started.
        
        Discontinuities in the value of this counter can occur at
        re-initialization of the SMB AO. The last discontinuity time is
        indicated by the value of cwoAoStatsLastResetTime for the SMB
        AO."
    ::= { cwoAoSmbxStats 2 }

cwoAoSmbxStatsBytesReadServer OBJECT-TYPE
    SYNTAX --?? syntax is not convertable to SMIv1
           Counter
--  Units
--    bytes
    ACCESS read-only
    STATUS mandatory
    DESCRIPTION
        "This object contains total number of bytes read from file
        servers by SMB Application Optimizer since it was started.
        
        Discontinuities in the value of this counter can occur at
        re-initialization of the SMB AO. The last discontinuity time is
        indicated by the value of cwoAoStatsLastResetTime for the SMB
        AO."
    ::= { cwoAoSmbxStats 3 }

cwoAoSmbxStatsBytesWriteServer OBJECT-TYPE
    SYNTAX --?? syntax is not convertable to SMIv1
           Counter
--  Units
--    bytes
    ACCESS read-only
    STATUS mandatory
    DESCRIPTION
        "This object contains total number of bytes written to file
        servers by SMB Application Optimizer since it was started.
        
        Discontinuities in the value of this counter can occur at
        re-initialization of the SMB AO. The last discontinuity time is
        indicated by the value of cwoAoStatsLastResetTime for the SMB
        AO."
    ::= { cwoAoSmbxStats 4 }

cwoAoSmbxStatsBytesReadClient OBJECT-TYPE
    SYNTAX --?? syntax is not convertable to SMIv1
           Counter
--  Units
--    bytes
    ACCESS read-only
    STATUS mandatory
    DESCRIPTION
        "This object contains total number of bytes read by SMB
        Application Optimizer clients since it was started.
        
        Discontinuities in the value of this counter can occur at
        re-initialization of the SMB AO. The last discontinuity time is
        indicated by the value of cwoAoStatsLastResetTime for the SMB
        AO."
    ::= { cwoAoSmbxStats 5 }

cwoAoSmbxStatsBytesWriteClient OBJECT-TYPE
    SYNTAX --?? syntax is not convertable to SMIv1
           Counter
--  Units
--    bytes
    ACCESS read-only
    STATUS mandatory
    DESCRIPTION
        "This object contains total number of bytes written by SMB
        Application optimizer clients since it was started.
        
        Discontinuities in the value of this counter can occur at
        re-initialization of the SMB AO. The last discontinuity time is
        indicated by the value of cwoAoStatsLastResetTime for the SMB
        AO."
    ::= { cwoAoSmbxStats 6 }

cwoAoSmbxStatsProcessedReqs OBJECT-TYPE
    SYNTAX --?? syntax is not convertable to SMIv1
           Counter
--  Units
--    requests
    ACCESS read-only
    STATUS mandatory
    DESCRIPTION
        "This object contains total number of requests processed by SMB
        Application Optimizer since it was started.
        
        Discontinuities in the value of this counter can occur at
        re-initialization of the SMB AO. The last discontinuity time is
        indicated by the value of cwoAoStatsLastResetTime for the SMB
        AO."
    ::= { cwoAoSmbxStats 7 }

cwoAoSmbxStatsActiveReqs OBJECT-TYPE
    SYNTAX --?? syntax is not convertable to SMIv1
           CounterBasedGauge64
--    Rsyntax Counter
--  Units
--    requests
    ACCESS read-only
    STATUS mandatory
    DESCRIPTION
        "This object contains total number of active requests getting
        processed by SMB Application Optimizer."
    ::= { cwoAoSmbxStats 8 }

cwoAoSmbxStatsTotalTimedOutReqs OBJECT-TYPE
    SYNTAX --?? syntax is not convertable to SMIv1
           Unsigned64
--    Rsyntax Counter
--  Units
--    requests
    ACCESS read-only
    STATUS mandatory
    DESCRIPTION
        "This object contains total number of requests timed out in SMB
        Application Optimizer since it was started.
        
        Discontinuities in the value of this counter can occur at
        re-initialization of the SMB AO. The last discontinuity time is
        indicated by the value of cwoAoStatsLastResetTime for the SMB
        AO."
    ::= { cwoAoSmbxStats 9 }

cwoAoSmbxStatsTotalRemoteReqs OBJECT-TYPE
    SYNTAX --?? syntax is not convertable to SMIv1
           Counter
--  Units
--    requests
    ACCESS read-only
    STATUS mandatory
    DESCRIPTION
        "This object contains total number of SMB requests sent to
        remote file server since SMB AO was started.
        
        Discontinuities in the value of this counter can occur at
        re-initialization of the SMB AO. The last discontinuity time is
        indicated by the value of cwoAoStatsLastResetTime for the SMB
        AO."
    ::= { cwoAoSmbxStats 10 }

cwoAoSmbxStatsTotalLocalReqs OBJECT-TYPE
    SYNTAX --?? syntax is not convertable to SMIv1
           Counter
--  Units
--    requests
    ACCESS read-only
    STATUS mandatory
    DESCRIPTION
        "This object contains total number of SMB requests served
        locally by SMB Application Optimizer since it was started.
        
        Discontinuities in the value of this counter can occur at
        re-initialization of the SMB AO. The last discontinuity time is
        indicated by the value of cwoAoStatsLastResetTime for the SMB
        AO."
    ::= { cwoAoSmbxStats 11 }

cwoAoSmbxStatsRemoteAvgTime OBJECT-TYPE
    SYNTAX CiscoMilliSeconds
--    Rsyntax Gauge
    ACCESS read-only
    STATUS mandatory
    DESCRIPTION
        "This object contains average duration of time taken by SMB
        Application Optimizer to process all remote requests since it
        was started.
        
        Discontinuities in the value of this counter can occur at
        re-initialization of the SMB AO. The last discontinuity time is
        indicated by the value of cwoAoStatsLastResetTime for the SMB
        AO."
    ::= { cwoAoSmbxStats 12 }

cwoAoSmbxStatsLocalAvgTime OBJECT-TYPE
    SYNTAX CiscoMilliSeconds
--    Rsyntax Gauge
    ACCESS read-only
    STATUS mandatory
    DESCRIPTION
        "This object contains average duration of time taken by SMB
        Application Optimizer to process all local requests since it
        was started.
        
        Discontinuities in the value of this counter can occur at
        re-initialization of the SMB AO. The last discontinuity time is
        indicated by the value of cwoAoStatsLastResetTime for the SMB
        AO."
    ::= { cwoAoSmbxStats 13 }

cwoAoSmbxStatsRACacheHitCount OBJECT-TYPE
    SYNTAX --?? syntax is not convertable to SMIv1
           Counter
    ACCESS read-only
    STATUS mandatory
    DESCRIPTION
        "This object contains SMB Application Optimizer Read Ahead Cache
        hit count since SMB AO was started.
        
        Discontinuities in the value of this counter can occur at
        re-initialization of the SMB AO. The last discontinuity time is
        indicated by the value of cwoAoStatsLastResetTime for the SMB
        AO."
    ::= { cwoAoSmbxStats 14 }

cwoAoSmbxStatsMDCacheHitCount OBJECT-TYPE
    SYNTAX --?? syntax is not convertable to SMIv1
           Counter
    ACCESS read-only
    STATUS mandatory
    DESCRIPTION
        "This object contains SMB Application Optimizer Metadata cache
        hit count since SMB AO was started.
        
        Discontinuities in the value of this counter can occur at
        re-initialization of the SMB AO. The last discontinuity time is
        indicated by the value of cwoAoStatsLastResetTime for the SMB
        AO."
    ::= { cwoAoSmbxStats 15 }

cwoAoSmbxStatsRACacheHitRate OBJECT-TYPE
    SYNTAX Gauge(0..100)
--  Units
--    percent
    ACCESS read-only
    STATUS mandatory
    DESCRIPTION
        "This object contains SMB Application Optimizer Read Ahead cache
        hit rate since it was started.
        
        Discontinuities in the value of this counter can occur at
        re-initialization of the SMB AO. The last discontinuity time is
        indicated by the value of cwoAoStatsLastResetTime for the SMB
        AO."
    ::= { cwoAoSmbxStats 16 }

cwoAoSmbxStatsMDCacheHitRate OBJECT-TYPE
    SYNTAX Gauge(0..100)
--  Units
--    percent
    ACCESS read-only
    STATUS mandatory
    DESCRIPTION
        "This object contains SMB Application Optimizer Metadata cache
        hit rate since it was started.
        
        Discontinuities in the value of this counter can occur at
        re-initialization of the SMB AO. The last discontinuity time is
        indicated by the value of cwoAoStatsLastResetTime for the SMB
        AO."
    ::= { cwoAoSmbxStats 17 }

cwoAoSmbxStatsMaxRACacheSize OBJECT-TYPE
    SYNTAX --?? syntax is not convertable to SMIv1
           Unsigned64
--    Rsyntax Counter
--  Units
--    bytes
    ACCESS read-only
    STATUS mandatory
    DESCRIPTION
        "This object contains Maximum disk space that can be allocated
        for Read Ahead data in SMB Application Optimizer cache."
    ::= { cwoAoSmbxStats 18 }

cwoAoSmbxStatsMaxMDCacheSize OBJECT-TYPE
    SYNTAX --?? syntax is not convertable to SMIv1
           Unsigned64
--    Rsyntax Counter
--  Units
--    bytes
    ACCESS read-only
    STATUS mandatory
    DESCRIPTION
        "This object contains maximum disk space that can be allocated
        for Metadata in SMB Application Optimizer cache."
    ::= { cwoAoSmbxStats 19 }

cwoAoSmbxStatsMDCacheSize OBJECT-TYPE
    SYNTAX --?? syntax is not convertable to SMIv1
           CounterBasedGauge64
--    Rsyntax Counter
--  Units
--    bytes
    ACCESS read-only
    STATUS mandatory
    DESCRIPTION
        "This object contains current size of Metadata cache in SMB
        Application Optimizer."
    ::= { cwoAoSmbxStats 20 }

cwoAoSmbxStatsRAEvictedAge OBJECT-TYPE
    SYNTAX CiscoMilliSeconds
--    Rsyntax Gauge
    ACCESS read-only
    STATUS mandatory
    DESCRIPTION
        "This object contains amount of time spent in the SMB
        Application Optimizer Read Ahead cache by the resource that was
        last evicted since last update. If this amount is too short or
        too long, it is recommended to modify the size of the cache."
    ::= { cwoAoSmbxStats 21 }

cwoAoSmbxStatsRTT OBJECT-TYPE
    SYNTAX TimeIntervalSec
--    Rsyntax Gauge
    ACCESS read-only
    STATUS mandatory
    DESCRIPTION
        "This object contains total round trip time for all SMB
        connections since it was started.
        
        Discontinuities in the value of this counter can occur at
        re-initialization of the SMB AO. The last discontinuity time is
        indicated by the value of cwoAoStatsLastResetTime for the SMB
        AO."
    ::= { cwoAoSmbxStats 22 }

cwoAoSmbxStatsTotalRespTimeSaving OBJECT-TYPE
    SYNTAX TimeIntervalSec
--    Rsyntax Gauge
    ACCESS read-only
    STATUS mandatory
    DESCRIPTION
        "This object contains total response time saved due to SMB AO
        optimizations since it was started.
        
        Discontinuities in the value of this counter can occur at
        re-initialization of the SMB AO. The last discontinuity time is
        indicated by the value of cwoAoStatsLastResetTime for the SMB
        AO."
    ::= { cwoAoSmbxStats 23 }

cwoAoSmbxStatsOpenFiles OBJECT-TYPE
    SYNTAX Gauge
--  Units
--    files
    ACCESS read-only
    STATUS mandatory
    DESCRIPTION
        "This object contains number of files currently opened by SMB
        Application Optimizer."
    ::= { cwoAoSmbxStats 24 }

cwoAoSmbxStatsTotalFilesInRACache OBJECT-TYPE
    SYNTAX Gauge
--  Units
--    files
    ACCESS read-only
    STATUS mandatory
    DESCRIPTION
        "This object contains total number of files in SMB Application
        optimizer Read Ahead cache."
    ::= { cwoAoSmbxStats 25 }

cwoAoSmbxStatsRdL4SignWANBytes OBJECT-TYPE
    SYNTAX --?? syntax is not convertable to SMIv1
           Counter
    ACCESS read-only
    STATUS mandatory
    DESCRIPTION
        "This object contains the total number of Layer 4 (L4) optimized
        signed bytes read from WAN by SMB Application Optimizer since
        the SMB Application Optimizer was started. L4 optimization
        comprises of TFO, DRE and LZ optimizations.
        
        Discontinuities in the value of this counter can occur at
        re-initialization of the SMB AO. The last discontinuity time is
        indicated by the value of cwoAoStatsLastResetTime for the SMB
        AO."
    ::= { cwoAoSmbxStats 26 }

cwoAoSmbxStatsWrL4SignWANBytes OBJECT-TYPE
    SYNTAX --?? syntax is not convertable to SMIv1
           Counter
    ACCESS read-only
    STATUS mandatory
    DESCRIPTION
        "This object contains the total number of Layer 4 (L4) optimized
        signed bytes written to WAN by SMB Application Optimizer since
        SMB Application Optimizer was started. L4 optimization comprises
        of TFO, DRE and LZ optimizations.
        
        Discontinuities in the value of this counter can occur at
        re-initialization of the SMB AO. The last discontinuity time is
        indicated by the value of cwoAoStatsLastResetTime for the SMB
        AO."
    ::= { cwoAoSmbxStats 27 }

cwoAoSmbxStatsRdSignLANBytes OBJECT-TYPE
    SYNTAX --?? syntax is not convertable to SMIv1
           Counter
    ACCESS read-only
    STATUS mandatory
    DESCRIPTION
        "This object contains the total number of signed bytes read from
        LAN by SMB Application Optimizer since the SMB Application
        Optimizer was started.
        
        Discontinuities in the value of this counter can occur at
        re-initialization of the SMB AO. The last discontinuity time is
        indicated by the value of cwoAoStatsLastResetTime for the SMB
        AO."
    ::= { cwoAoSmbxStats 28 }

cwoAoSmbxStatsWrSignLANBytes OBJECT-TYPE
    SYNTAX --?? syntax is not convertable to SMIv1
           Counter
    ACCESS read-only
    STATUS mandatory
    DESCRIPTION
        "This object contains the total number of original signed bytes
        written to LAN by SMB Application Optimizer since SMB
        Application Optimizer was started.
        
        Discontinuities in the value of this counter can occur at
        re-initialization of the SMB AO. The last discontinuity time is
        indicated by the value of cwoAoStatsLastResetTime for the SMB
        AO."
    ::= { cwoAoSmbxStats 29 }

cwoAoHttpxStatsTotalSavedTime OBJECT-TYPE
    SYNTAX CiscoMilliSeconds
--    Rsyntax Gauge
--  Units
--    milliseconds
    ACCESS read-only
    STATUS mandatory
    DESCRIPTION
        "This object indicates total time saved due to optimizations
        done by HTTP AO since it was started.
        
        Discontinuities in the value of this counter can occur at
        re-initialization of the HTTP AO. The last discontinuity time is
        indicated by the value of cwoAoStatsLastResetTime for the HTTP
        AO."
    ::= { cwoAoHttpxStats 1 }

cwoAoHttpxStatsTotalRTT OBJECT-TYPE
    SYNTAX CiscoMilliSeconds
--    Rsyntax Gauge
--  Units
--    milliseconds
    ACCESS read-only
    STATUS mandatory
    DESCRIPTION
        "This object indicates total Round Trip Time (RTT) for all the
        connections going through HTTP AO since it was started.
        
        Discontinuities in the value of this counter can occur at
        re-initialization of the HTTP AO. The last discontinuity time is
        indicated by the value of cwoAoStatsLastResetTime for the HTTP
        AO."
    ::= { cwoAoHttpxStats 2 }

cwoAoHttpxStatsTotalMDCMTime OBJECT-TYPE
    SYNTAX CiscoMilliSeconds
--    Rsyntax Gauge
--  Units
--    milliseconds
    ACCESS read-only
    STATUS mandatory
    DESCRIPTION
        "This object indicates total time for Meta Data Cache Misses
        (MDCM) for HTTP AO since it was started.
        
        Discontinuities in the value of this counter can occur at
        re-initialization of the HTTP AO. The last discontinuity time is
        indicated by the value of cwoAoStatsLastResetTime for the HTTP
        AO."
    ::= { cwoAoHttpxStats 3 }

cwoAoHttpxStatsEstSavedTime OBJECT-TYPE
    SYNTAX Gauge(0..100)
--  Units
--    percent
    ACCESS read-only
    STATUS mandatory
    DESCRIPTION
        "This object indicates percentage estimated time saved due to
        optimizations done by HTTP AO since it was started."
    ::= { cwoAoHttpxStats 4 }

cwoAoHttpxStatsTotalSPSessions OBJECT-TYPE
    SYNTAX --?? syntax is not convertable to SMIv1
           Counter
--  Units
--    sessions
    ACCESS read-only
    STATUS mandatory
    DESCRIPTION
        "This object indicates the total number of SharePoint Optimized
        HTTP sessions. This counter is incremented for every
        session on which SharePoint optimization can be performed. An
        HTTP session is tagged as a SharePoint Session based on the
        information present in the HTTP request."
    ::= { cwoAoHttpxStats 5 }

cwoAoHttpxStatsTotalSPPFSessions OBJECT-TYPE
    SYNTAX --?? syntax is not convertable to SMIv1
           Counter
--  Units
--    sessions
    ACCESS read-only
    STATUS mandatory
    DESCRIPTION
        "This object indicates the total number of SharePoint Pre-fetch
        optimized HTTP sessions. This counter is incremented
        for every session on which SharePoint pre-fetch optimization
        can be performed. An HTTP session is tagged as a SharePoint
        pre-fetch Session based on the information present in the HTTP
        request. A pre-fetch operation is one where the edge WAAS
        device fetches the next set of data (which it anticipates the
        client will request later) from the server based on the current
        HTTP Request information."
    ::= { cwoAoHttpxStats 6 }

cwoAoHttpxStatsTotalSPPFObjects OBJECT-TYPE
    SYNTAX --?? syntax is not convertable to SMIv1
           Counter
--  Units
--    requests
    ACCESS read-only
    STATUS mandatory
    DESCRIPTION
        "This object indicates the total number of pre-fetched objects
        served locally for SharePoint pre-fetch sessions. The edge WAAS
        device maintains a local cache where the pre-fetched responses
        are saved. This object is incremented whenever the SharePoint
        client request is served from the pre-fetch cache."
    ::= { cwoAoHttpxStats 7 }

cwoAoHttpxStatsTotalSPRTTSaved OBJECT-TYPE
    SYNTAX --?? syntax is not convertable to SMIv1
           Counter
--  Units
--    milliseconds
    ACCESS read-only
    STATUS mandatory
    DESCRIPTION
        "This object contains total Round Trip Time (RTT) saved due to
        SharePoint pre-fetch optimizations since SharePoint pre-fetch
        optimization was started.
        
        Discontinuities in the value of this counter can occur at
        re-initialization of the HTTP AO. The last discontinuity time is
        indicated by the value of cwoAoStatsLastResetTime for the HTTP
        AO."
    ::= { cwoAoHttpxStats 8 }

cwoAoHttpxStatsTotalSPPFMissTime OBJECT-TYPE
    SYNTAX --?? syntax is not convertable to SMIv1
           Counter
--  Units
--    milliseconds
    ACCESS read-only
    STATUS mandatory
    DESCRIPTION
        "This object indicates total time for SharePoint pre-fetch
        Cache Misses since SharePoint pre-fetch optimization  was
        started.
        
        Discontinuities in the value of this counter can occur at
        re-initialization of the HTTP AO. The last discontinuity time is
        indicated by the value of cwoAoStatsLastResetTime for the HTTP
        AO."
    ::= { cwoAoHttpxStats 9 }

cwoAoMapixStatsUnEncrALRT OBJECT-TYPE
    SYNTAX CiscoMilliSeconds
--    Rsyntax Gauge
--  Units
--    milliseconds
    ACCESS read-only
    STATUS mandatory
    DESCRIPTION
        "This object indicates Average Local Response Time (ALRT) for
        unencrypted connections of MAPI AO since it was started."
    ::= { cwoAoMapixStats 1 }

cwoAoMapixStatsEncrALRT OBJECT-TYPE
    SYNTAX CiscoMilliSeconds
--    Rsyntax Gauge
--  Units
--    milliseconds
    ACCESS read-only
    STATUS mandatory
    DESCRIPTION
        "This object indicates Average Local Response Time (ALRT) for
        encrypted connections of MAPI AO since it was started."
    ::= { cwoAoMapixStats 2 }

cwoAoMapixStatsUnEncrARRT OBJECT-TYPE
    SYNTAX CiscoMilliSeconds
--    Rsyntax Gauge
--  Units
--    milliseconds
    ACCESS read-only
    STATUS mandatory
    DESCRIPTION
        "This object indicates Average Remote Response Time (ARRT) for
        unencrypted connections of MAPI AO since it was started."
    ::= { cwoAoMapixStats 3 }

cwoAoMapixStatsEncrARRT OBJECT-TYPE
    SYNTAX CiscoMilliSeconds
--    Rsyntax Gauge
--  Units
--    milliseconds
    ACCESS read-only
    STATUS mandatory
    DESCRIPTION
        "This object indicates Average Remote Response Time (ARRT) for
        encrypted connections of MAPI AO since it was started."
    ::= { cwoAoMapixStats 4 }

cwoAoMapixStatsTotalUnEncrLRs OBJECT-TYPE
    SYNTAX --?? syntax is not convertable to SMIv1
           Counter
--  Units
--    requests
    ACCESS read-only
    STATUS mandatory
    DESCRIPTION
        "This object indicates total requests served locally for
        unencrypted connections by MAPI AO since it was started.
        
        Discontinuities in the value of this counter can occur at
        re-initialization of the MAPI AO. The last discontinuity time is
        indicated by the value of cwoAoStatsLastResetTime for the MAPI
        AO."
    ::= { cwoAoMapixStats 5 }

cwoAoMapixStatsTotalEncrLRs OBJECT-TYPE
    SYNTAX --?? syntax is not convertable to SMIv1
           Counter
--  Units
--    requests
    ACCESS read-only
    STATUS mandatory
    DESCRIPTION
        "This object indicates total requests served locally for
        encrypted connections by MAPI AO since it was started.
        
        Discontinuities in the value of this counter can occur at
        re-initialization of the MAPI AO. The last discontinuity time is
        indicated by the value of cwoAoStatsLastResetTime for the MAPI
        AO."
    ::= { cwoAoMapixStats 6 }

cwoAoMapixStatsTotalUnEncrRRs OBJECT-TYPE
    SYNTAX --?? syntax is not convertable to SMIv1
           Counter
--  Units
--    requests
    ACCESS read-only
    STATUS mandatory
    DESCRIPTION
        "This object indicates total Remote Requests(RR) served by
        remote servers for unencrypted connections of MAPI AO since it
        was started.
        
        Discontinuities in the value of this counter can occur at
        re-initialization of the MAPI AO. The last discontinuity time is
        indicated by the value of cwoAoStatsLastResetTime for the MAPI
        AO."
    ::= { cwoAoMapixStats 7 }

cwoAoMapixStatsTotalEncrRRs OBJECT-TYPE
    SYNTAX --?? syntax is not convertable to SMIv1
           Counter
--  Units
--    requests
    ACCESS read-only
    STATUS mandatory
    DESCRIPTION
        "This object indicates total Remote Requests(RR) served by
        remote servers for encrypted connections by MAPI AO since it
        was started.
        
        Discontinuities in the value of this counter can occur at
        re-initialization of the MAPI AO. The last discontinuity time is
        indicated by the value of cwoAoStatsLastResetTime for the MAPI
        AO."
    ::= { cwoAoMapixStats 8 }

cwoAoMapixStatsUnEncrAvgRedTime OBJECT-TYPE
    SYNTAX CiscoMilliSeconds
--    Rsyntax Gauge
--  Units
--    milliseconds
    ACCESS read-only
    STATUS mandatory
    DESCRIPTION
        "This object indicates average time reduced for unencrypted
        connections due to optimizations done by MAPI AO since it was
        started.
        
        Discontinuities in the value of this counter can occur at
        re-initialization of the MAPI AO. The last discontinuity time is
        indicated by the value of cwoAoStatsLastResetTime for the MAPI
        AO."
    ::= { cwoAoMapixStats 9 }

cwoAoMapixStatsEncrAvgRedTime OBJECT-TYPE
    SYNTAX CiscoMilliSeconds
--    Rsyntax Gauge
--  Units
--    milliseconds
    ACCESS read-only
    STATUS mandatory
    DESCRIPTION
        "This object indicates average time reduced for encrypted
        connections due to optimizations done by MAPI AO since it was
        started.
        
        Discontinuities in the value of this counter can occur at
        re-initialization of the MAPI AO. The last discontinuity time is
        indicated by the value of cwoAoStatsLastResetTime for the MAPI
        AO."
    ::= { cwoAoMapixStats 10 }

cwoAoNfsxStatsALRT OBJECT-TYPE
    SYNTAX CiscoMilliSeconds
--    Rsyntax Gauge
--  Units
--    milliseconds
    ACCESS read-only
    STATUS mandatory
    DESCRIPTION
        "This object indicates Average Local Response Time (ALRT) for
        NFS AO since it was started."
    ::= { cwoAoNfsxStats 1 }

cwoAoNfsxStatsARRT OBJECT-TYPE
    SYNTAX CiscoMilliSeconds
--    Rsyntax Gauge
--  Units
--    milliseconds
    ACCESS read-only
    STATUS mandatory
    DESCRIPTION
        "This object indicates Average Remote Response Time (ARRT) for
        NFS AO since it was started."
    ::= { cwoAoNfsxStats 2 }

cwoAoNfsxStatsTotalLRs OBJECT-TYPE
    SYNTAX --?? syntax is not convertable to SMIv1
           Counter
--  Units
--    requests
    ACCESS read-only
    STATUS mandatory
    DESCRIPTION
        "This object indicates total requests served locally by NFS AO
        since it was started.
        
        Discontinuities in the value of this counter can occur at
        re-initialization of the NFS AO. The last discontinuity time is
        indicated by the value of cwoAoStatsLastResetTime for the NFS
        AO."
    ::= { cwoAoNfsxStats 3 }

cwoAoNfsxStatsTotalRRs OBJECT-TYPE
    SYNTAX --?? syntax is not convertable to SMIv1
           Counter
--  Units
--    requests
    ACCESS read-only
    STATUS mandatory
    DESCRIPTION
        "This object indicates total Remote Requests (RR) served by
        remote servers for NFS AO since it was started.
        
        Discontinuities in the value of this counter can occur at
        re-initialization of the NFS AO. The last discontinuity time is
        indicated by the value of cwoAoStatsLastResetTime for the NFS
        AO."
    ::= { cwoAoNfsxStats 4 }

cwoAoNfsxStatsEstTimeSaved OBJECT-TYPE
    SYNTAX Gauge(0..100)
--  Units
--    percent
    ACCESS read-only
    STATUS mandatory
    DESCRIPTION
        "This object indicates percentage estimated time saved due to
        optimizations done by NFS AO since it was started."
    ::= { cwoAoNfsxStats 5 }

cwoAoVideoxStatsTotalInBytes OBJECT-TYPE
    SYNTAX --?? syntax is not convertable to SMIv1
           Counter
--  Units
--    bytes
    ACCESS read-only
    STATUS mandatory
    DESCRIPTION
        "This object indicates total incoming bytes for Video AO since
        it was started.
        
        Discontinuities in the value of this counter can occur at
        re-initialization of the Video AO. The last discontinuity time
        is indicated by the value of cwoAoStatsLastResetTime for the
        Video AO."
    ::= { cwoAoVideoxStats 1 }

cwoAoVideoxStatsTotalOutBytes OBJECT-TYPE
    SYNTAX --?? syntax is not convertable to SMIv1
           Counter
--  Units
--    bytes
    ACCESS read-only
    STATUS mandatory
    DESCRIPTION
        "This object indicates total outgoing bytes for Video AO since
        it was started.
        
        Discontinuities in the value of this counter can occur at
        re-initialization of the Video AO. The last discontinuity time
        is indicated by the value of cwoAoStatsLastResetTime for the
        Video AO."
    ::= { cwoAoVideoxStats 2 }

cwoAoCifsxStatsTotalReadBytes OBJECT-TYPE
    SYNTAX Counter
--  Units
--    kilo-bytes
    ACCESS read-only
    STATUS mandatory
    DESCRIPTION
        "This object indicates the total bytes read by clients
        from the client side (via cache or remotely) using CIFS AO
        since CIFS AO was started.
        
        Discontinuities in the value of this counter can occur at
        re-initialization of the CIFS AO. The last discontinuity time is
        indicated by the value of cwoAoStatsLastResetTime for the CIFS
        AO."
    ::= { cwoAoCifsxStats 1 }

cwoAoCifsxStatsTotalWrittenBytes OBJECT-TYPE
    SYNTAX Counter
--  Units
--    kilo-bytes
    ACCESS read-only
    STATUS mandatory
    DESCRIPTION
        "This object indicates the total bytes written to the
        client-side using the CIFS AO since CIFS AO was started.
        
        Discontinuities in the value of this counter can occur at
        re-initialization of the CIFS AO. The last discontinuity time is
        indicated by the value of cwoAoStatsLastResetTime for the CIFS
        AO."
    ::= { cwoAoCifsxStats 2 }

cwoAoCifsxStatsTotalRemoteReqs OBJECT-TYPE
    SYNTAX Counter
--  Units
--    requests
    ACCESS read-only
    STATUS mandatory
    DESCRIPTION
        "This object indicates the total requests sent to remote file
        server since CIFS AO was started.
        
        Discontinuities in the value of this counter can occur at
        re-initialization of the CIFS AO. The last discontinuity time is
        indicated by the value of cwoAoStatsLastResetTime for the CIFS
        AO."
    ::= { cwoAoCifsxStats 3 }

cwoAoCifsxStatsTotalLocalReqs OBJECT-TYPE
    SYNTAX Counter
--  Units
--    requests
    ACCESS read-only
    STATUS mandatory
    DESCRIPTION
        "This object indicates the total number requests served locally
        by CIFS AO since it was started.
        
        Discontinuities in the value of this counter can occur at
        re-initialization of the CIFS AO. The last discontinuity time is
        indicated by the value of cwoAoStatsLastResetTime for the CIFS
        AO."
    ::= { cwoAoCifsxStats 4 }

cwoAoCifsxStatsTotalRemoteTime OBJECT-TYPE
    SYNTAX CiscoMilliSeconds
--    Rsyntax Gauge
--  Units
--    milliseconds
    ACCESS read-only
    STATUS mandatory
    DESCRIPTION
        "This object indicates the total duration of time taken by CIFS
        AO to process all remote requests since CIFS AO was started.
        
        Discontinuities in the value of this counter can occur at
        re-initialization of the CIFS AO. The last discontinuity time is
        indicated by the value of cwoAoStatsLastResetTime for the CIFS
        AO."
    ::= { cwoAoCifsxStats 5 }

cwoAoCifsxStatsTotalLocalTime OBJECT-TYPE
    SYNTAX CiscoMilliSeconds
--    Rsyntax Gauge
--  Units
--    milliseconds
    ACCESS read-only
    STATUS mandatory
    DESCRIPTION
        "This object indicates the total duration of time taken by CIFS
        AO to process all local requests since CIFS AO was started.
        
        Discontinuities in the value of this counter can occur at
        re-initialization of the CIFS AO. The last discontinuity time is
        indicated by the value of cwoAoStatsLastResetTime for the CIFS
        AO."
    ::= { cwoAoCifsxStats 6 }

cwoAoCifsxStatsConnectedSessions OBJECT-TYPE
    SYNTAX Gauge
--  Units
--    sessions
    ACCESS read-only
    STATUS mandatory
    DESCRIPTION
        "This object indicates the number of currently connected CIFS
        sessions."
    ::= { cwoAoCifsxStats 7 }

cwoAoCifsxStatsOpenFiles OBJECT-TYPE
    SYNTAX Gauge
--  Units
--    files
    ACCESS read-only
    STATUS mandatory
    DESCRIPTION
        "This object indicates the number of currently open CIFS files."
    ::= { cwoAoCifsxStats 8 }

cwoAoCifsxStatsMaxCacheSize OBJECT-TYPE
    SYNTAX Gauge
--  Units
--    kilo-bytes
    ACCESS read-only
    STATUS mandatory
    DESCRIPTION
        "This object indicates the maximum disk space (in KB) allocated
        for data in the CIFS AO cache."
    ::= { cwoAoCifsxStats 9 }

cwoAoCifsxStatsCurrentCacheSize OBJECT-TYPE
    SYNTAX Gauge
--  Units
--    kilo-bytes
    ACCESS read-only
    STATUS mandatory
    DESCRIPTION
        "This object indicates the amount of disk space (in KB),
        currently being used for data in the CIFS AO cache."
    ::= { cwoAoCifsxStats 10 }

cwoAoCifsxStatsMaxCacheResources OBJECT-TYPE
    SYNTAX Gauge
--  Units
--    files
    ACCESS read-only
    STATUS mandatory
    DESCRIPTION
        "This object indicates the maximum number of cache resources
        (files and directories) supported by the CIFS AO cache,
        regardless of the size of these resources."
    ::= { cwoAoCifsxStats 11 }

cwoAoCifsxStatsCacheResources OBJECT-TYPE
    SYNTAX Gauge
--  Units
--    files
    ACCESS read-only
    STATUS mandatory
    DESCRIPTION
        "This object indicates the number of cache resources (files
        and directories) currently held in the CIFS AO cache."
    ::= { cwoAoCifsxStats 12 }

cwoAoCifsxStatsEvictedResources OBJECT-TYPE
    SYNTAX Counter
--  Units
--    files
    ACCESS read-only
    STATUS mandatory
    DESCRIPTION
        "This object indicates the number of cache resources (files and
        directories) that have been evicted from the cache since CIFS
        AO was started.
        
        Discontinuities in the value of this counter can occur at
        re-initialization of the CIFS AO. The last discontinuity time is
        indicated by the value of cwoAoStatsLastResetTime for the CIFS
        AO."
    ::= { cwoAoCifsxStats 13 }

cwoAoCifsxStatsLastEvictedTime OBJECT-TYPE
    SYNTAX TimeStamp
--    Rsyntax TimeTicks
    ACCESS read-only
    STATUS mandatory
    DESCRIPTION
        "This object indicates the time when cache resources (files and
        directories) were last evicted from the CIFS AO cache. 00:00 is
        displayed if no cache resources have been evicted since CIFS AO
        was started."
    ::= { cwoAoCifsxStats 14 }

cwoAoCifsxStatsVolHiWatermark OBJECT-TYPE
    SYNTAX Gauge(0..100)
--  Units
--    percent
    ACCESS read-only
    STATUS mandatory
    DESCRIPTION
        "This object indicates the disk usage high watermark in
        percentage that triggers the eviction of resources from the
        CIFS AO cache."
    ::= { cwoAoCifsxStats 15 }

cwoAoCifsxStatsVolLoWatermark OBJECT-TYPE
    SYNTAX Gauge(0..100)
--  Units
--    percent
    ACCESS read-only
    STATUS mandatory
    DESCRIPTION
        "This object indicates the target disk usage low watermark
        percentage to be reached via cache eviction when triggered by
        cfVolHiWatermark. When this low watermark is reached, cache
        eviction stops."
    ::= { cwoAoCifsxStats 16 }

cwoAoCifsxStatsAmntHiWatermark OBJECT-TYPE
    SYNTAX Gauge(0..100)
--  Units
--    percent
    ACCESS read-only
    STATUS mandatory
    DESCRIPTION
        "This object indicates the target percentage of maximum cache
        resources (defined by cfMaxCacheResources) that triggers the
        eviction of resources from the CIFS AO cache."
    ::= { cwoAoCifsxStats 17 }

cwoAoCifsxStatsAmntLoWatermark OBJECT-TYPE
    SYNTAX Gauge(0..100)
--  Units
--    percent
    ACCESS read-only
    STATUS mandatory
    DESCRIPTION
        "This object indicates the target percentage of maximum cache
        resources (defined by cfMaxCacheResources) to be reached via
        cache eviction when triggered by cfAmntHiWatermark. When this
        low watermark is reached, cache eviction stops."
    ::= { cwoAoCifsxStats 18 }

cwoAoCifsxStatsEvictedAge OBJECT-TYPE
    SYNTAX TimeInterval
--    Rsyntax INTEGER(0..2147483647)
    ACCESS read-only
    STATUS mandatory
    DESCRIPTION
        "This object indicates the amount of time spent in the CIFS AO
        cache by the resource that was last evicted. If this amount is
        too short or too long, it is recommended to modify the size of
        the cache."
    ::= { cwoAoCifsxStats 19 }

cwoAoCifsxStatsEvictedLastAccess OBJECT-TYPE
    SYNTAX TimeStamp
--    Rsyntax TimeTicks
    ACCESS read-only
    STATUS mandatory
    DESCRIPTION
        "This object indicates the value of sysUpTime when the resource,
        which was last evicted from the CIFS AO cache has been last
        accessed."
    ::= { cwoAoCifsxStats 20 }

cwoAoCifsxStatsFFTotalReqs OBJECT-TYPE
    SYNTAX --?? syntax is not convertable to SMIv1
           Counter
--  Units
--    requests
    ACCESS read-only
    STATUS mandatory
    DESCRIPTION
        "This object contains total number of FindFirst (FF) requests
        since CIFS AO was started.
        
        Discontinuities in the value of this counter can occur at
        re-initialization of the CIFS AO. The last discontinuity time is
        indicated by the value of cwoAoStatsLastResetTime for the CIFS
        AO."
    ::= { cwoAoCifsxStats 21 }

cwoAoCifsxStatsFFRemoteReqs OBJECT-TYPE
    SYNTAX --?? syntax is not convertable to SMIv1
           Counter
--  Units
--    requests
    ACCESS read-only
    STATUS mandatory
    DESCRIPTION
        "This object contains total number of FindFirst (FF) requests
        sent to the remote file-server since CIFS AO was started.
        
        Discontinuities in the value of this counter can occur at
        re-initialization of the CIFS AO. The last discontinuity time is
        indicated by the value of cwoAoStatsLastResetTime for the CIFS
        AO."
    ::= { cwoAoCifsxStats 22 }

cwoAoCifsxStatsFFLocalRespTime OBJECT-TYPE
    SYNTAX CiscoMilliSeconds
--    Rsyntax Gauge
--  Units
--    milliseconds
    ACCESS read-only
    STATUS mandatory
    DESCRIPTION
        "This object contains the average local response time for
        FindFirst (FF) requests replied locally since CIFS AO was
        started.
        
        Discontinuities in the value of this counter can occur at
        re-initialization of the CIFS AO. The last discontinuity time is
        indicated by the value of cwoAoStatsLastResetTime for the CIFS
        AO."
    ::= { cwoAoCifsxStats 23 }

cwoAoCifsxStatsFFRemoteRespTime OBJECT-TYPE
    SYNTAX CiscoMilliSeconds
--    Rsyntax Gauge
--  Units
--    milliseconds
    ACCESS read-only
    STATUS mandatory
    DESCRIPTION
        "This object contains the average remote response time for
        FindFirst (FF) requests replied remotely since CIFS AO was
        started.
        
        Discontinuities in the value of this counter can occur at
        re-initialization of the CIFS AO. The last discontinuity time is
        indicated by the value of cwoAoStatsLastResetTime for the CIFS
        AO."
    ::= { cwoAoCifsxStats 24 }

cwoAoCifsxStatsDirResources OBJECT-TYPE
    SYNTAX Gauge
--  Units
--    files
    ACCESS read-only
    STATUS mandatory
    DESCRIPTION
        "This object contains the total number of currently allocated
        Directory Resources in CIFS AO."
    ::= { cwoAoCifsxStats 25 }

cwoAppStatsTable OBJECT-TYPE
    SYNTAX SEQUENCE OF CwoAppStatsEntry
    ACCESS not-accessible
    STATUS mandatory
    DESCRIPTION
        "This table lists the statistics for applications configured on
        the wan optimization system."
    ::= { cwoApp 1 }

cwoAppStatsEntry OBJECT-TYPE
    SYNTAX CwoAppStatsEntry
    ACCESS not-accessible
    STATUS mandatory
    DESCRIPTION
        "An entry describing statistics for applications configured on
        the WAN optimization system. The WAN opimitization system
        creates an entry when a user configures an application for
        optimization. The WAN optimization system deletes an entry, when
        user removes the application from the configuration."
    INDEX { cwoAppStatsAppName }
    ::= { cwoAppStatsTable 1 }

CwoAppStatsEntry ::= SEQUENCE {
    cwoAppStatsAppName SnmpAdminString,
    cwoAppStatsOriginalBytes Counter,
    cwoAppStatsOptimizedBytes Counter,
    cwoAppStatsPTBytes Counter
    }

cwoAppStatsAppName OBJECT-TYPE
    SYNTAX SnmpAdminString
--    Rsyntax OCTET STRING(SIZE(0..255))
    ACCESS not-accessible
    STATUS mandatory
    DESCRIPTION
        "This object indicates the name of a particular application,
        which is configured for optimization."
    ::= { cwoAppStatsEntry 1 }

cwoAppStatsOriginalBytes OBJECT-TYPE
    SYNTAX --?? syntax is not convertable to SMIv1
           Counter
--  Units
--    bytes
    ACCESS read-only
    STATUS mandatory
    DESCRIPTION
        "This object indicates total original traffic (uncompressed) in
        bytes of a particular application that has entered into the
        system."
    ::= { cwoAppStatsEntry 2 }

cwoAppStatsOptimizedBytes OBJECT-TYPE
    SYNTAX --?? syntax is not convertable to SMIv1
           Counter
--  Units
--    bytes
    ACCESS read-only
    STATUS mandatory
    DESCRIPTION
        "This object indicates total optimized traffic in bytes of a
        particular application."
    ::= { cwoAppStatsEntry 3 }

cwoAppStatsPTBytes OBJECT-TYPE
    SYNTAX --?? syntax is not convertable to SMIv1
           Counter
--  Units
--    bytes
    ACCESS read-only
    STATUS mandatory
    DESCRIPTION
        "This object indicates total pass-through traffic in bytes of a
        particular application."
    ::= { cwoAppStatsEntry 4 }

cwoPmapStatsTable OBJECT-TYPE
    SYNTAX SEQUENCE OF CwoPmapStatsEntry
    ACCESS not-accessible
    STATUS mandatory
    DESCRIPTION
        "This table lists the staistics for active policy maps."
    ::= { cwoPmap 1 }

cwoPmapStatsEntry OBJECT-TYPE
    SYNTAX CwoPmapStatsEntry
    ACCESS not-accessible
    STATUS mandatory
    DESCRIPTION
        "An entry describing statistics related with an active policy
        map of a given type. The WAN optimization system creates/deletes
        an entry for a policy map when it is made active/inactive
        through configuration changes."
    INDEX { cwoPmapStatsType, cwoPmapStatsName }
    ::= { cwoPmapStatsTable 1 }

CwoPmapStatsEntry ::= SEQUENCE {
    cwoPmapStatsType CwoTypes,
    cwoPmapStatsName SnmpAdminString,
    cwoPmapStatsDescr SnmpAdminString,
    cwoPmapStatsTotalConns Counter,
    cwoPmapStatsTotalBytes Counter,
    cwoPmapStatsTotalPTConns Counter,
    cwoPmapStatsTotalPTBytes Counter
    }

cwoPmapStatsType OBJECT-TYPE
    SYNTAX CwoTypes
--    Rsyntax INTEGER {
--        waas(1),
--        appnav(2)
--        }
    ACCESS not-accessible
    STATUS mandatory
    DESCRIPTION
        "This object indicates type of the policy map."
    ::= { cwoPmapStatsEntry 1 }

cwoPmapStatsName OBJECT-TYPE
    SYNTAX SnmpAdminString
--    Rsyntax OCTET STRING(SIZE(0..255))
    ACCESS not-accessible
    STATUS mandatory
    DESCRIPTION
        "This object indicates name of the policy map."
    ::= { cwoPmapStatsEntry 2 }

cwoPmapStatsDescr OBJECT-TYPE
    SYNTAX SnmpAdminString
--    Rsyntax OCTET STRING(SIZE(0..255))
    ACCESS read-only
    STATUS mandatory
    DESCRIPTION
        "This object indicates the descriptive information of the policy
        map configured on the WAN optimization system. If the
        description is not configured for a given policy map then this
        string will contain a NULL string."
    ::= { cwoPmapStatsEntry 3 }

cwoPmapStatsTotalConns OBJECT-TYPE
    SYNTAX --?? syntax is not convertable to SMIv1
           Counter
--  Units
--    connections
    ACCESS read-only
    STATUS mandatory
    DESCRIPTION
        "This object indicates total number of connections processed by
        the policy map since it is active."
    ::= { cwoPmapStatsEntry 4 }

cwoPmapStatsTotalBytes OBJECT-TYPE
    SYNTAX --?? syntax is not convertable to SMIv1
           Counter
--  Units
--    kilo-bytes
    ACCESS read-only
    STATUS mandatory
    DESCRIPTION
        "This object indicates total bytes processed by the policy map
        since it is active."
    ::= { cwoPmapStatsEntry 5 }

cwoPmapStatsTotalPTConns OBJECT-TYPE
    SYNTAX --?? syntax is not convertable to SMIv1
           Counter
--  Units
--    connections
    ACCESS read-only
    STATUS mandatory
    DESCRIPTION
        "This object indicates total connections, which are made
        as pass-through due to some reason by the policy map since it
        is
        active."
    ::= { cwoPmapStatsEntry 6 }

cwoPmapStatsTotalPTBytes OBJECT-TYPE
    SYNTAX --?? syntax is not convertable to SMIv1
           Counter
--  Units
--    kilo-bytes
    ACCESS read-only
    STATUS mandatory
    DESCRIPTION
        "This object indicates total bytes which are made pass-through
        by the policy map since it is active."
    ::= { cwoPmapStatsEntry 7 }

cwoCmapStatsTable OBJECT-TYPE
    SYNTAX SEQUENCE OF CwoCmapStatsEntry
    ACCESS not-accessible
    STATUS mandatory
    DESCRIPTION
        "This table lists the staistics for class maps associated with
        the active policy map."
    ::= { cwoCmap 1 }

cwoCmapStatsEntry OBJECT-TYPE
    SYNTAX CwoCmapStatsEntry
    ACCESS not-accessible
    STATUS mandatory
    DESCRIPTION
        "An entry describes statistics for the class maps associated
        with active policy maps. A new entry will be created for the
        class map when a new class map gets associated to the policy map
        through the configuration changes. An entry will be deleted,
        when the class map is disassociated from the active policy map
        through the configuration changes."
    INDEX { cwoCmapStatsType, cwoCmapStatsName }
    ::= { cwoCmapStatsTable 1 }

CwoCmapStatsEntry ::= SEQUENCE {
    cwoCmapStatsType CwoTypes,
    cwoCmapStatsName SnmpAdminString,
    cwoCmapStatsDescr SnmpAdminString,
    cwoCmapStatsTotalConns Counter,
    cwoCmapStatsTotalBytes Counter,
    cwoCmapStatsTotalPTConns Counter,
    cwoCmapStatsTotalPTBytes Counter
    }

cwoCmapStatsType OBJECT-TYPE
    SYNTAX CwoTypes
--    Rsyntax INTEGER {
--        waas(1),
--        appnav(2)
--        }
    ACCESS not-accessible
    STATUS mandatory
    DESCRIPTION
        "This object indicates the type of the class map."
    ::= { cwoCmapStatsEntry 1 }

cwoCmapStatsName OBJECT-TYPE
    SYNTAX SnmpAdminString
--    Rsyntax OCTET STRING(SIZE(0..255))
    ACCESS not-accessible
    STATUS mandatory
    DESCRIPTION
        "This object indicates the name of the class map."
    ::= { cwoCmapStatsEntry 2 }

cwoCmapStatsDescr OBJECT-TYPE
    SYNTAX SnmpAdminString
--    Rsyntax OCTET STRING(SIZE(0..255))
    ACCESS read-only
    STATUS mandatory
    DESCRIPTION
        "This object indicates the descriptive information of the class
        map configured on the WAN optimization system. If the
        description is not configured for a given class map then this
        string will contain a NULL string."
    ::= { cwoCmapStatsEntry 3 }

cwoCmapStatsTotalConns OBJECT-TYPE
    SYNTAX --?? syntax is not convertable to SMIv1
           Counter
--  Units
--    connections
    ACCESS read-only
    STATUS mandatory
    DESCRIPTION
        "This object indicates the total number of connections processed
        by the class map."
    ::= { cwoCmapStatsEntry 4 }

cwoCmapStatsTotalBytes OBJECT-TYPE
    SYNTAX --?? syntax is not convertable to SMIv1
           Counter
--  Units
--    bytes
    ACCESS read-only
    STATUS mandatory
    DESCRIPTION
        "This object indicates the total bytes processed by the
        class map."
    ::= { cwoCmapStatsEntry 5 }

cwoCmapStatsTotalPTConns OBJECT-TYPE
    SYNTAX --?? syntax is not convertable to SMIv1
           Counter
--  Units
--    connections
    ACCESS read-only
    STATUS mandatory
    DESCRIPTION
        "This object indicates total connections, which are made
        as pass-through due to some reason by the class map."
    ::= { cwoCmapStatsEntry 6 }

cwoCmapStatsTotalPTBytes OBJECT-TYPE
    SYNTAX --?? syntax is not convertable to SMIv1
           Counter
--  Units
--    bytes
    ACCESS read-only
    STATUS mandatory
    DESCRIPTION
        "This object indicates the total bytes which are made
        pass-through by the class map."
    ::= { cwoCmapStatsEntry 7 }

cwoTfoConnectionOverload TRAP-TYPE
-- Reverse mappable trap
    ENTERPRISE ciscoWanOptimizationMIB
    VARIABLES {
        cwoTfoStatsMaxActiveConn }
--  Status
--    mandatory
    DESCRIPTION
        "This notification indicates that the device has reached its
        limit of number of connections it can optimize. No new
        connections will be picked-up for optimization, while the device
        is in this state."
    ::= 1

cwoPeerOverload TRAP-TYPE
-- Reverse mappable trap
    ENTERPRISE ciscoWanOptimizationMIB
    VARIABLES {
        cwoGeneralMaxActivePeers }
--  Status
--    mandatory
    DESCRIPTION
        "This notification indicates the device has reached its limit of
        number of peer devices with which it can optimize connections.
        While the device is in this state, connections from new peer
        device will not be picked-up for optimization."
    ::= 2

cwoCpuThrottlingOn TRAP-TYPE
-- Reverse mappable trap
    ENTERPRISE ciscoWanOptimizationMIB
    VARIABLES {
        cwoGeneralCpuThrottleHigh, cwoGeneralCpuThrottlPeriod, 
        cpmCPUTotalMonIntervalValue }
--  Status
--    mandatory
    DESCRIPTION
        "This notification indicates that the device has detected that
        the current CPU utilization (stored in
        cpmCPUTotalMonIntervalValue) is higher than the
        cwoGeneralCpuThrottleHigh. As a result the device has entered
        into a throttling mode due to which connections under
        optimization may experience slowdown. This notification is
        generated the moment it occurs after a time lapse of 30 minutes
        since the previous notification."
    ::= 3

cwoCpuThrottlingOff TRAP-TYPE
-- Reverse mappable trap
    ENTERPRISE ciscoWanOptimizationMIB
    VARIABLES {
        cwoGeneralCpuThrottleLow, cwoGeneralCpuThrottlPeriod, 
        cpmCPUTotalMonIntervalValue }
--  Status
--    mandatory
    DESCRIPTION
        "This notification indicates that device has detected that the
        CPU utilization of device (stored in
        cpmCPUTotalMonIntervalValue) has fallen below the
        cwoGeneralCpuThrottleLow from cwoGeneralCpuThrottleHigh. As a
        result the device has come out of the throttling mode and there
        should not be any negative impact of CPU usage on connection
        under optimization. This notification is generated the moment it
        occurs after a time lapse of 30 minutes since the previous
        notification."
    ::= 4

cwoLicenseExpired TRAP-TYPE
-- Reverse mappable trap
    ENTERPRISE ciscoWanOptimizationMIB
--  Status
--    mandatory
    DESCRIPTION
        "This notification is generated when the license on the system
        expires after the period for which it was installed."
    ::= 5

cwoLicenseRevoked TRAP-TYPE
-- Reverse mappable trap
    ENTERPRISE ciscoWanOptimizationMIB
--  Status
--    mandatory
    DESCRIPTION
        "This notification is generated when a requested revoke ticket
        is obtained. This ticket could have been requested in order to
        move the license to a different system."
    ::= 6

cwoLicenseDeleted TRAP-TYPE
-- Reverse mappable trap
    ENTERPRISE ciscoWanOptimizationMIB
--  Status
--    mandatory
    DESCRIPTION
        "This notification is generated when the license on the system
        is cleared."
    ::= 7

cwoGeneralGroup OBJECT IDENTIFIER ::= { ciscoWanOptimizationMIBGroups 1 }
-- OBJECT-GROUP
--  Status
--    mandatory
--  Descr
--    This collection of objects represent the general statistics of
--    WAN optimization system/sub-system.
--  objects
--    cwoGeneralActivePeers, cwoGeneralMaxActivePeers, 
--    cwoGeneralCpuThrottleHigh, cwoGeneralCpuThrottleLow, 
--    cwoGeneralCpuThrottlPeriod

cwoTfoBaseGroup OBJECT IDENTIFIER ::= { ciscoWanOptimizationMIBGroups 2 }
-- OBJECT-GROUP
--  Status
--    mandatory
--  Descr
--    This collection of objects represent the common statistics for
--    TFO.
--  objects
--    cwoTfoStatsTotalOptConn, cwoTfoStatsActiveOptConn, 
--    cwoTfoStatsMaxActiveConn, cwoTfoStatsTotalNormalClosedConn, 
--    cwoTfoStatsResetConn

cwoTfoExtGroup OBJECT IDENTIFIER ::= { ciscoWanOptimizationMIBGroups 3 }
-- OBJECT-GROUP
--  Status
--    mandatory
--  Descr
--    This collection of objects represent the statistics for
--    TFO, which are optional.
--  objects
--    cwoTfoStatsActiveOptTCPPlusConn, 
--    cwoTfoStatsActiveOptTCPOnlyConn, 
--    cwoTfoStatsActiveOptTCPPrepConn, cwoTfoStatsActiveADConn, 
--    cwoTfoStatsReservedConn, cwoTfoStatsPendingConn, 
--    cwoTfoStatsActivePTConn

cwoAoStatsGroup OBJECT IDENTIFIER ::= { ciscoWanOptimizationMIBGroups 4 }
-- OBJECT-GROUP
--  Status
--    mandatory
--  Descr
--    This group includes statistics for AO. Which are common for all
--    AOs.
--  objects
--    cwoAoStatsIsConfigured, cwoAoStatsIsLicensed, 
--    cwoAoStatsOperationalState, cwoAoStatsStartUpTime, 
--    cwoAoStatsTotalHandledConns, cwoAoStatsTotalOptConns, 
--    cwoAoStatsTotalHandedOffConns, cwoAoStatsTotalDroppedConns, 
--    cwoAoStatsActiveOptConns, cwoAoStatsPendingConns, 
--    cwoAoStatsMaxActiveOptConns, cwoAoStatsLastResetTime

cwoAoSmbExtendedStatsGroup OBJECT IDENTIFIER ::= { ciscoWanOptimizationMIBGroups 7 }
-- OBJECT-GROUP
--  Status
--    mandatory
--  Descr
--    This Group contains statistics which are specific to SMB AO.
--  objects
--    cwoAoSmbxStatsBytesReadCache, cwoAoSmbxStatsBytesWriteCache, 
--    cwoAoSmbxStatsBytesReadServer, cwoAoSmbxStatsBytesWriteServer, 
--    cwoAoSmbxStatsBytesReadClient, cwoAoSmbxStatsBytesWriteClient, 
--    cwoAoSmbxStatsProcessedReqs, cwoAoSmbxStatsActiveReqs, 
--    cwoAoSmbxStatsTotalTimedOutReqs, 
--    cwoAoSmbxStatsTotalRemoteReqs, cwoAoSmbxStatsTotalLocalReqs, 
--    cwoAoSmbxStatsRemoteAvgTime, cwoAoSmbxStatsLocalAvgTime, 
--    cwoAoSmbxStatsRACacheHitCount, cwoAoSmbxStatsMDCacheHitCount, 
--    cwoAoSmbxStatsRACacheHitRate, cwoAoSmbxStatsMDCacheHitRate, 
--    cwoAoSmbxStatsMaxRACacheSize, cwoAoSmbxStatsMaxMDCacheSize, 
--    cwoAoSmbxStatsMDCacheSize, cwoAoSmbxStatsRAEvictedAge, 
--    cwoAoSmbxStatsRTT, cwoAoSmbxStatsTotalRespTimeSaving, 
--    cwoAoSmbxStatsOpenFiles, cwoAoSmbxStatsTotalFilesInRACache

cwoAoHttpExtendedStatsGroup OBJECT IDENTIFIER ::= { ciscoWanOptimizationMIBGroups 9 }
-- OBJECT-GROUP
--  Status
--    mandatory
--  Descr
--    This group contains statistics which are specific to HTTP AO.
--  objects
--    cwoAoHttpxStatsTotalSavedTime, cwoAoHttpxStatsTotalRTT, 
--    cwoAoHttpxStatsTotalMDCMTime, cwoAoHttpxStatsEstSavedTime

cwoAoMapiExtendedStatsGroup OBJECT IDENTIFIER ::= { ciscoWanOptimizationMIBGroups 10 }
-- OBJECT-GROUP
--  Status
--    mandatory
--  Descr
--    This group contains statistics which are specific to MAPI AO.
--  objects
--    cwoAoMapixStatsUnEncrALRT, cwoAoMapixStatsUnEncrARRT, 
--    cwoAoMapixStatsTotalUnEncrLRs, cwoAoMapixStatsTotalUnEncrRRs, 
--    cwoAoMapixStatsUnEncrAvgRedTime, cwoAoMapixStatsEncrALRT, 
--    cwoAoMapixStatsEncrARRT, cwoAoMapixStatsTotalEncrLRs, 
--    cwoAoMapixStatsTotalEncrRRs, cwoAoMapixStatsEncrAvgRedTime

cwoAoNfsExtendedStatsGroup OBJECT IDENTIFIER ::= { ciscoWanOptimizationMIBGroups 11 }
-- OBJECT-GROUP
--  Status
--    mandatory
--  Descr
--    This group contains statistics which are specific to NFS AO.
--  objects
--    cwoAoNfsxStatsALRT, cwoAoNfsxStatsARRT, 
--    cwoAoNfsxStatsTotalLRs, cwoAoNfsxStatsTotalRRs, 
--    cwoAoNfsxStatsEstTimeSaved

cwoAoVideoExtendedStatsGroup OBJECT IDENTIFIER ::= { ciscoWanOptimizationMIBGroups 12 }
-- OBJECT-GROUP
--  Status
--    mandatory
--  Descr
--    This group contains statistics which are specific to Video AO.
--  objects
--    cwoAoVideoxStatsTotalInBytes, cwoAoVideoxStatsTotalOutBytes

cwoAoCifsExtendedStatsGroup OBJECT IDENTIFIER ::= { ciscoWanOptimizationMIBGroups 13 }
-- OBJECT-GROUP
--  Status
--    mandatory
--  Descr
--    This group contains statistics which are specific to CIFS AO.
--  objects
--    cwoAoCifsxStatsTotalReadBytes, 
--    cwoAoCifsxStatsTotalWrittenBytes, 
--    cwoAoCifsxStatsTotalRemoteReqs, cwoAoCifsxStatsTotalLocalReqs, 
--    cwoAoCifsxStatsTotalRemoteTime, cwoAoCifsxStatsTotalLocalTime, 
--    cwoAoCifsxStatsConnectedSessions, cwoAoCifsxStatsOpenFiles, 
--    cwoAoCifsxStatsMaxCacheSize, cwoAoCifsxStatsCurrentCacheSize, 
--    cwoAoCifsxStatsMaxCacheResources, 
--    cwoAoCifsxStatsCacheResources, 
--    cwoAoCifsxStatsEvictedResources, 
--    cwoAoCifsxStatsLastEvictedTime, cwoAoCifsxStatsVolHiWatermark, 
--    cwoAoCifsxStatsVolLoWatermark, cwoAoCifsxStatsAmntHiWatermark, 
--    cwoAoCifsxStatsAmntLoWatermark, cwoAoCifsxStatsEvictedAge, 
--    cwoAoCifsxStatsEvictedLastAccess

cwoAoApplicationStatsGroup OBJECT IDENTIFIER ::= { ciscoWanOptimizationMIBGroups 14 }
-- OBJECT-GROUP
--  Status
--    mandatory
--  Descr
--    This group contains statistics for applications associated with
--    AO.
--  objects
--    cwoAppStatsOriginalBytes, cwoAppStatsOptimizedBytes, 
--    cwoAppStatsPTBytes

cwoAoPolicyMapStatsGroup OBJECT IDENTIFIER ::= { ciscoWanOptimizationMIBGroups 15 }
-- OBJECT-GROUP
--  Status
--    mandatory
--  Descr
--    This group contains statistics for active policy map.
--  objects
--    cwoPmapStatsDescr, cwoPmapStatsTotalConns, 
--    cwoPmapStatsTotalBytes, cwoPmapStatsTotalPTConns, 
--    cwoPmapStatsTotalPTBytes

cwoAoClassMapStatsGroup OBJECT IDENTIFIER ::= { ciscoWanOptimizationMIBGroups 16 }
-- OBJECT-GROUP
--  Status
--    mandatory
--  Descr
--    This group contains statistics for class maps associated with
--    active policy map.
--  objects
--    cwoCmapStatsDescr, cwoCmapStatsTotalConns, 
--    cwoCmapStatsTotalBytes, cwoCmapStatsTotalPTConns, 
--    cwoCmapStatsTotalPTBytes

cwoAoStatsGroupRev1 OBJECT IDENTIFIER ::= { ciscoWanOptimizationMIBGroups 17 }
-- OBJECT-GROUP
--  Status
--    mandatory
--  Descr
--    This group includes statistics, which are common for all AOs.
--  objects
--    cwoAoStatsLoadStatus, cwoAoStatsBwOpt

cwoAoTfoExtGroupRev1 OBJECT IDENTIFIER ::= { ciscoWanOptimizationMIBGroups 18 }
-- OBJECT-GROUP
--  Status
--    mandatory
--  Descr
--    This collection of objects represent the statistics for TFO,
--    which are optional.
--  objects
--    cwoTfoStatsLoadStatus

cwoAoHttpExtendedStatsGroupRev1 OBJECT IDENTIFIER ::= { ciscoWanOptimizationMIBGroups 19 }
-- OBJECT-GROUP
--  Status
--    mandatory
--  Descr
--    This group contains statistics specific to cwoAoHttpxStats
--    group enhancement and SharePoint AO.
--  objects
--    cwoAoHttpxStatsTotalSPSessions, 
--    cwoAoHttpxStatsTotalSPPFSessions, 
--    cwoAoHttpxStatsTotalSPPFObjects, 
--    cwoAoHttpxStatsTotalSPRTTSaved, 
--    cwoAoHttpxStatsTotalSPPFMissTime

cwoAoCifsExtendedStatsGroupRev1 OBJECT IDENTIFIER ::= { ciscoWanOptimizationMIBGroups 20 }
-- OBJECT-GROUP
--  Status
--    mandatory
--  Descr
--    This group contains statistics specific to CIFS Atkins
--    feature.
--  objects
--    cwoAoCifsxStatsFFTotalReqs, cwoAoCifsxStatsFFRemoteReqs, 
--    cwoAoCifsxStatsFFLocalRespTime, 
--    cwoAoCifsxStatsFFRemoteRespTime, cwoAoCifsxStatsDirResources

cwoAoSmbExtendedStatsGroupRev1 OBJECT IDENTIFIER ::= { ciscoWanOptimizationMIBGroups 21 }
-- OBJECT-GROUP
--  Status
--    mandatory
--  Descr
--    This group contains statistics specific to Signed Bytes
--    Statistics feature for SMB AO.
--  objects
--    cwoAoSmbxStatsRdL4SignWANBytes, 
--    cwoAoSmbxStatsWrL4SignWANBytes, cwoAoSmbxStatsRdSignLANBytes, 
--    cwoAoSmbxStatsWrSignLANBytes

cwoOverloadNotificationGroup OBJECT IDENTIFIER ::= { ciscoWanOptimizationMIBGroups 5 }
-- NOTIFICATION-GROUP
--  Status
--    mandatory
--  Descr
--    This group contains notifications event for various overload
--    condition on wan optimization system.
--  notifications
--    cwoTfoConnectionOverload, cwoPeerOverload

cwoCpuNotificationGroup OBJECT IDENTIFIER ::= { ciscoWanOptimizationMIBGroups 6 }
-- NOTIFICATION-GROUP
--  Status
--    mandatory
--  Descr
--    This group contains notifications event for wan optimization
--    system, which are specific to some WAN optimization systems.
--  notifications
--    cwoCpuThrottlingOn, cwoCpuThrottlingOff

cwoLicenseNotificationGroup OBJECT IDENTIFIER ::= { ciscoWanOptimizationMIBGroups 8 }
-- NOTIFICATION-GROUP
--  Status
--    mandatory
--  Descr
--    This group contains notifications event for actions on
--    licensing on wan optimization systems.
--  notifications
--    cwoLicenseExpired, cwoLicenseRevoked, cwoLicenseDeleted

ciscoWanOptimizationMIBCompliance OBJECT IDENTIFIER ::= { ciscoWanOptimizationMIBCompliances 1 }
-- MODULE-COMPLIANCE
--  Status
--    deprecated
--  Descr
--    This is a default module-compliance containing default object
--    groups.
--  Module
--    >>current<<
--   MandGroup
--    cwoTfoBaseGroup
--   MandGroup
--    cwoOverloadNotificationGroup
--   OptGroup
--    cwoGeneralGroup
--   OptGroup
--    cwoTfoExtGroup
--   OptGroup
--    cwoAoStatsGroup
--   OptGroup
--    cwoCpuNotificationGroup
--   OptGroup
--    cwoAoSmbExtendedStatsGroup

ciscoWanOptimizationMIBCompliance1 OBJECT IDENTIFIER ::= { ciscoWanOptimizationMIBCompliances 2 }
-- MODULE-COMPLIANCE
--  Status
--    deprecated
--  Descr
--    This is a default module-compliance containing default object
--    groups.
--  Module
--    >>current<<
--   MandGroup
--    cwoTfoBaseGroup
--   MandGroup
--    cwoOverloadNotificationGroup
--   OptGroup
--    cwoGeneralGroup
--   OptGroup
--    cwoTfoExtGroup
--   OptGroup
--    cwoAoStatsGroup
--   OptGroup
--    cwoCpuNotificationGroup
--   OptGroup
--    cwoAoSmbExtendedStatsGroup
--   OptGroup
--    cwoLicenseNotificationGroup

ciscoWanOptimizationMIBComplianceRev2 OBJECT IDENTIFIER ::= { ciscoWanOptimizationMIBCompliances 3 }
-- MODULE-COMPLIANCE
--  Status
--    deprecated
--  Descr
--    This is a default module-compliance containing default object
--    groups. This compliance module deprecates 
--    ciscoWanOptimizationMIBCompliance1.
--  Module
--    >>current<<
--   MandGroup
--    cwoTfoBaseGroup
--   OptGroup
--    cwoGeneralGroup
--   OptGroup
--    cwoCpuNotificationGroup
--   OptGroup
--    cwoOverloadNotificationGroup
--   OptGroup
--    cwoLicenseNotificationGroup
--   OptGroup
--    cwoAoHttpExtendedStatsGroup
--   OptGroup
--    cwoAoMapiExtendedStatsGroup
--   OptGroup
--    cwoAoNfsExtendedStatsGroup
--   OptGroup
--    cwoAoVideoExtendedStatsGroup
--   OptGroup
--    cwoAoCifsExtendedStatsGroup
--   OptGroup
--    cwoAoApplicationStatsGroup
--   OptGroup
--    cwoAoPolicyMapStatsGroup
--   OptGroup
--    cwoAoClassMapStatsGroup
--   OptGroup
--    cwoAoStatsGroupRev1
--   OptGroup
--    cwoAoTfoExtGroupRev1
--   OptGroup
--    cwoTfoExtGroup
--   OptGroup
--    cwoAoStatsGroup
--   OptGroup
--    cwoAoSmbExtendedStatsGroup

ciscoWanOptimizationMIBComplianceRev3 OBJECT IDENTIFIER ::= { ciscoWanOptimizationMIBCompliances 4 }
-- MODULE-COMPLIANCE
--  Status
--    deprecated
--  Descr
--    This is a default module-compliance containing default object
--    groups. This compliance module deprecates 
--    ciscoWanOptimizationMIBComplianceRev2.
--  Module
--    >>current<<
--   MandGroup
--    cwoTfoBaseGroup
--   OptGroup
--    cwoGeneralGroup
--   OptGroup
--    cwoCpuNotificationGroup
--   OptGroup
--    cwoOverloadNotificationGroup
--   OptGroup
--    cwoLicenseNotificationGroup
--   OptGroup
--    cwoAoHttpExtendedStatsGroup
--   OptGroup
--    cwoAoMapiExtendedStatsGroup
--   OptGroup
--    cwoAoNfsExtendedStatsGroup
--   OptGroup
--    cwoAoVideoExtendedStatsGroup
--   OptGroup
--    cwoAoCifsExtendedStatsGroup
--   OptGroup
--    cwoAoApplicationStatsGroup
--   OptGroup
--    cwoAoPolicyMapStatsGroup
--   OptGroup
--    cwoAoClassMapStatsGroup
--   OptGroup
--    cwoAoStatsGroupRev1
--   OptGroup
--    cwoAoTfoExtGroupRev1
--   OptGroup
--    cwoTfoExtGroup
--   OptGroup
--    cwoAoStatsGroup
--   OptGroup
--    cwoAoSmbExtendedStatsGroup
--   OptGroup
--    cwoAoHttpExtendedStatsGroupRev1
--   OptGroup
--    cwoAoCifsExtendedStatsGroupRev1

ciscoWanOptimizationMIBComplianceRev4 OBJECT IDENTIFIER ::= { ciscoWanOptimizationMIBCompliances 5 }
-- MODULE-COMPLIANCE
--  Status
--    mandatory
--  Descr
--    This is a default module-compliance containing default object
--    groups. This compliance module deprecates 
--    ciscoWanOptimizationMIBComplianceRev3.
--  Module
--    >>current<<
--   MandGroup
--    cwoTfoBaseGroup
--   OptGroup
--    cwoGeneralGroup
--   OptGroup
--    cwoCpuNotificationGroup
--   OptGroup
--    cwoOverloadNotificationGroup
--   OptGroup
--    cwoLicenseNotificationGroup
--   OptGroup
--    cwoAoHttpExtendedStatsGroup
--   OptGroup
--    cwoAoMapiExtendedStatsGroup
--   OptGroup
--    cwoAoNfsExtendedStatsGroup
--   OptGroup
--    cwoAoVideoExtendedStatsGroup
--   OptGroup
--    cwoAoCifsExtendedStatsGroup
--   OptGroup
--    cwoAoApplicationStatsGroup
--   OptGroup
--    cwoAoPolicyMapStatsGroup
--   OptGroup
--    cwoAoClassMapStatsGroup
--   OptGroup
--    cwoAoStatsGroup
--   OptGroup
--    cwoAoTfoExtGroupRev1
--   OptGroup
--    cwoTfoExtGroup
--   OptGroup
--    cwoAoStatsGroupRev1
--   OptGroup
--    cwoAoSmbExtendedStatsGroup
--   OptGroup
--    cwoAoHttpExtendedStatsGroupRev1
--   OptGroup
--    cwoAoCifsExtendedStatsGroupRev1
--   OptGroup
--    cwoAoSmbExtendedStatsGroupRev1


END
